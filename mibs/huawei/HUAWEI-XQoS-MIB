-- =================================================================
-- Copyright (C) 2004 by  HUAWEI TECHNOLOGIES. All rights reserved
-- 
-- Description: This mib file is used for management of huawei Class Based 
--              QoS information. 
-- Reference:
-- Version:     V2.20
-- History:
--              v1.0 tianli,2004.4.10,publish  
--              v1.1
--                  modified by chengang
--                  modified by zhangwenwu
--                  modified by wanglili
--                  modified by hezhifeng
--                  modified by dongling
--                  modified by tongtingting
--              V2.18
--                  modified by chenlong  
--              V2.19
--                  modified by suxunjin 
--              v2.20
--                  modified by lixinzhuo
-- =================================================================

HUAWEI-XQoS-MIB DEFINITIONS ::= BEGIN

    IMPORTS
        hwDatacomm
            FROM HUAWEI-MIB
        EnabledStatus            
            FROM P-BRIDGE-MIB  
        InterfaceIndex            
            FROM IF-MIB
        OBJECT-GROUP, MODULE-COMPLIANCE, NOTIFICATION-GROUP
            FROM SNMPv2-CONF            
        Integer32, Counter32, Counter64, Unsigned32, IpAddress, TimeTicks, OBJECT-TYPE, MODULE-IDENTITY, NOTIFICATION-TYPE            
            FROM SNMPv2-SMI
        RowStatus, MacAddress, TEXTUAL-CONVENTION
            FROM SNMPv2-TC;

    --BaType         
    BaType ::= TEXTUAL-CONVENTION
        STATUS  current  
        DESCRIPTION
            "The Direction Policy apply on."                 
        SYNTAX  INTEGER { 
            vlan8021p (1),
            dscp (2),
            mplsExp(3),
            ipPri(4),
            hqosVlan8021p(5),
            hqosDscp(6),
            hqosMplsExp(7),
            hqosIpPri(8),
            vlan8021pInbound(9)
            }


    hwXQoSMIB MODULE-IDENTITY 
        LAST-UPDATED "201404091525Z"        -- April 9, 2014 at 15:25 GMT
        ORGANIZATION 
            "Huawei Technologies Co.,Ltd."
        CONTACT-INFO 
            "Huawei Industrial Base
  Bantian, Longgang
   Shenzhen 518129
   People's Republic of China
   Website: http://www.huawei.com
   Email: support@huawei.com
 "
        DESCRIPTION 
            "The HUAWEI-XQoS-MIB contains objects to 
            Manage configuration and Monitor running state 
            for Class Based QoS feature."   
			
	   REVISION "201404091525Z"
       DESCRIPTION
          "ADD hwXQoSIf8021PCarCfgInfoTable "
		  
       REVISION "201309291428Z"
       DESCRIPTION
          "MOD hwXQoSCarTable OID"

       REVISION "201307291428Z"
       DESCRIPTION
          "ADD hwXQosCarResourceTable"
                   
       REVISION "201306031428Z"
       DESCRIPTION
          "MOD hwXQoSProfileObjects and hwXQoSPortQueueAlarmObjects OID"

       REVISION "201304271428Z"
       DESCRIPTION
          "ADD hwXQoSPortQueueStatisticsQueuePercentage NODE"
       
       REVISION "201312161428Z"
       DESCRIPTION
          "MOD hwXQoSCarTable and hwXQoSIfCarCfgInfoTable"
 
       REVISION "201401181428Z"
       DESCRIPTION
          "MOD hwXQoSIfQueueRunInfoTable and hwXQoSPortQueueStatisticsTable"          

      REVISION "201401221428Z"
       DESCRIPTION
          "ADD hwXQoSPortQueueAlarmExTable" 
		  
      REVISION "201403311428Z"
       DESCRIPTION
          "MOD hwXQoSBufferUsageStatisticsObjects OID"	
          
      REVISION "201404241428Z"
       DESCRIPTION
          "MOD hwXQoSProfileName NODE"		  
        ::= { hwQoS 4 }    

--   1.3.6.1.4.1.2011.5.25.32.4          
-- 
-- Textual conventions
-- 
-- 
-- type definitions in the interface queue
-- 
-- hwXQosQueueType
    XQosQueueType ::= TEXTUAL-CONVENTION
        STATUS current
        DESCRIPTION 
            "Queue Type:                               
            BE (1)
            AF1(2)
            AF2(3)
            AF3(4)
            AF4(5)
            EF (6)
            "
        SYNTAX INTEGER
            {
            be(1),
            af1(2),
            af2(3),
            af3(4),
            af4(5),
            ef(6)
            }

-- ResetFlag
    ResetFlag ::= TEXTUAL-CONVENTION
        STATUS current
        DESCRIPTION 
            "Reset Flag:                               
            DISABLE (0)
            RESET   (1)
            ENABLE  (2)           
            "
        SYNTAX INTEGER
            {
            disable(0),
            reset(1),
            enable(2)
            }

--    COS Type
    CosType ::= TEXTUAL-CONVENTION
        STATUS current
        DESCRIPTION 
            "
            BE(1)
            AF1(2)
            AF2(3)
            AF3(4)
            AF4(5)
            EF(6)
            CS6(7)
            CS7(8)
            ALL(9)
            queue10(10)
            queue11(11)
            queue12(12)
            queue13(13)
            queue14(14)
            queue15(15)
            queue16(16)
            queue17(17)
            queue18(18)
            queue19(19)
            queue20(20)
            queue21(21) 
            queue22(22)
            queue23(23)
            queue24(24)

            "
        SYNTAX INTEGER
            {
            be(1),
            af1(2),
            af2(3),
            af3(4),
            af4(5),
            ef(6),
            cs6(7),
            cs7(8),
            all(9),
            queue10(10),
            queue11(11),
            queue12(12),
            queue13(13),
            queue14(14),
            queue15(15),
            queue16(16),
            queue17(17),
            queue18(18),
            queue19(19),
            queue20(20),
            queue21(21), 
            queue22(22),
            queue23(23),
            queue24(24)
            }

--   CarAction         
    CarAction ::= TEXTUAL-CONVENTION
        STATUS current
        DESCRIPTION 
            "The actions taken when packets conforming or exceeding the configured 
            CIR:
                pass (1),
                discard (2),
                remark IP Precedence (3),
                remark DSCP(4),
                remark Mpls Exp(5),                                               
                remark (6),     
                remark 8021p(7)
            "
        SYNTAX INTEGER
            {
            pass(1),
            discard(2),
            remarkIpPrec(3),
            remarkDscp(4),
            remarkMplsExp(5),
            remark(6),  
            remark8021p(7)
            }

--   Direction         
    DirectionType ::= TEXTUAL-CONVENTION
        STATUS current
        DESCRIPTION 
            "The Direction Policy apply on."
        SYNTAX INTEGER
            {
            inbound(1),
            outbound(2)
            }

--   UrpfCtrlType
    UrpfCtrlType ::= TEXTUAL-CONVENTION
        STATUS current
        DESCRIPTION 
            "Strict(1)
            Loose(2)"
        SYNTAX INTEGER
            {
            strict(1),
            loose(2)
            }

--   SampleType              
    SampleType ::= TEXTUAL-CONVENTION
        STATUS current
        DESCRIPTION 
            "Fix-packets(1)
            Fix-time(2)
            Random-packets(3)
            Random-time(4)
            "
        SYNTAX INTEGER
            {
            fix-packets(1),
            fix-time(2),
            random-packets(3),
            random-time(4)
            }
              
-- IPCARRuleType
        IPCARRuleType ::= TEXTUAL-CONVENTION
            STATUS current
            DESCRIPTION 
                "Type of IPCAR Rule. "
            SYNTAX INTEGER
                {
                ipv4Acl(1),
                ipv4SrcIp(2),
                ipv4DstIp(3)
                }   
  
--
-- Node definitions
--

-- 1.3.6.1.4.1.2011.5.25.32
    hwQoS OBJECT IDENTIFIER ::= { hwDatacomm 32 }
    
--  1.3.6.1.4.1.2011.5.25.32.4.1
    hwXQoSObjects OBJECT IDENTIFIER ::= { hwXQoSMIB 1 }
    hwXQoSConformance OBJECT IDENTIFIER ::= { hwXQoSMIB 2 } 
    
--   BA command 
    hwXQoSBaObjects OBJECT IDENTIFIER ::= { hwXQoSObjects 1 }

--    Diffserv Domain        
    hwXQoSBaCfgInfoTable OBJECT-TYPE
        SYNTAX SEQUENCE OF HwXQoSBaCfgInfoEntry
        MAX-ACCESS not-accessible
        STATUS current
        DESCRIPTION
            "A table of diff-server domain configuration information."
        ::= { hwXQoSBaObjects 1 }

    hwXQoSBaCfgInfoEntry OBJECT-TYPE
        SYNTAX HwXQoSBaCfgInfoEntry
        MAX-ACCESS not-accessible
        STATUS current
        DESCRIPTION
            "Diff-server domain Information Entry."
        INDEX { hwXQoSBaIndex }
        ::= { hwXQoSBaCfgInfoTable 1 }

    HwXQoSBaCfgInfoEntry ::=
        SEQUENCE { 
            hwXQoSBaIndex
                Integer32,
            hwXQoSBaName
                OCTET STRING,
            hwXQoSBaRowStatus
                RowStatus
         }

    hwXQoSBaIndex OBJECT-TYPE
        SYNTAX Integer32
        MAX-ACCESS read-only
        STATUS current
        DESCRIPTION
            "The value of this object identifies the index of a DS domain.The value ranges from 0 to 7.This object has no default value."
        ::= { hwXQoSBaCfgInfoEntry 1 }

    hwXQoSBaName OBJECT-TYPE
        SYNTAX OCTET STRING (SIZE (1..8))
        MAX-ACCESS read-create
        STATUS current
        DESCRIPTION
            "This object indicates the name of a DS domain.The value of this object is a string of 1 to 8 ASCII characters in plain text and complies with the format of the command line.The object has no default value."
        ::= { hwXQoSBaCfgInfoEntry 2 }

    hwXQoSBaRowStatus OBJECT-TYPE
        SYNTAX RowStatus
        MAX-ACCESS read-create
        STATUS current
        DESCRIPTION
            "The value of this object identifies the row status.The value of this object can be any of the following:CreateAndGo(4),Destroy(6),Active(1).The object has no default value."
        ::= { hwXQoSBaCfgInfoEntry 3 }

--    8021p-inbound in diff domain        
    hwXQoSBa8021pPhbCfgInfoTable OBJECT-TYPE
        SYNTAX SEQUENCE OF HwXQoSBa8021pPhbCfgInfoEntry
        MAX-ACCESS not-accessible
        STATUS current
        DESCRIPTION
            "A table of diff-serve domain 8021p phb configuration information."
        ::= { hwXQoSBaObjects 2 }

    hwXQoSBa8021pPhbCfgInfoEntry OBJECT-TYPE
        SYNTAX HwXQoSBa8021pPhbCfgInfoEntry
        MAX-ACCESS not-accessible
        STATUS current
        DESCRIPTION
            "Diff-serve domain 8021p phb Configuration Information Entry."
        INDEX { hwXQoSBaIndex, hwXQoSBa8021pPhbIndex }
        ::= { hwXQoSBa8021pPhbCfgInfoTable 1 }

    HwXQoSBa8021pPhbCfgInfoEntry ::=
        SEQUENCE { 
            hwXQoSBa8021pPhbIndex
                Integer32,
            hwXQoSBa8021pPhbPri
                Integer32,
            hwXQoSBa8021pPhbCos
                Integer32,
            hwXQoSBa8021pPhbColour
                Integer32,
            hwXQoSBa8021pPhbRowStatus
                RowStatus
         }

    hwXQoSBa8021pPhbIndex OBJECT-TYPE
        SYNTAX Integer32
        MAX-ACCESS read-only
        STATUS current
        DESCRIPTION
            "The value of this object identifies the index of the Per-Hop Behavior (PHB)."
        ::= { hwXQoSBa8021pPhbCfgInfoEntry 1 }

    hwXQoSBa8021pPhbPri OBJECT-TYPE
        SYNTAX Integer32
        MAX-ACCESS read-only
        STATUS current
        DESCRIPTION
            "The value of this object identifies the 802.1p priority.The value ranges from 0 to 7."
        ::= { hwXQoSBa8021pPhbCfgInfoEntry 2 }

    hwXQoSBa8021pPhbCos OBJECT-TYPE
        SYNTAX Integer32
        MAX-ACCESS read-write
        STATUS current
        DESCRIPTION
            "The value of this object identifies CoS, that is, the scheduling priority.The value can be any of the following:CS7(7),CS6(6),EF(5),AF4(4),AF3(3),AF2(2),AF1(1),BE(0)."
        ::= { hwXQoSBa8021pPhbCfgInfoEntry 3 }

    hwXQoSBa8021pPhbColour OBJECT-TYPE
        SYNTAX Integer32
        MAX-ACCESS read-write
        STATUS current
        DESCRIPTION
            "The value of this object identifies the color of the packet, that is, the discarding priority.The value can be any of the following:Green(0),Yellow(1),Red(2)."
        ::= { hwXQoSBa8021pPhbCfgInfoEntry 4 }

    hwXQoSBa8021pPhbRowStatus OBJECT-TYPE
        SYNTAX RowStatus
        MAX-ACCESS read-create
        STATUS current
        DESCRIPTION
            "The value of this object identifies the row status.The value can be any of the following:CreateAndGo(4),Destroy(6),Active(1)."
        ::= { hwXQoSBa8021pPhbCfgInfoEntry 5 }

--    8021p-outbound in diff domain        
    hwXQoSBa8021pMapCfgInfoTable OBJECT-TYPE
        SYNTAX SEQUENCE OF HwXQoSBa8021pMapCfgInfoEntry
        MAX-ACCESS not-accessible
        STATUS current
        DESCRIPTION
            "A table of diff-serve domain 8021p map configuration information."
        ::= { hwXQoSBaObjects 3 }

    hwXQoSBa8021pMapCfgInfoEntry OBJECT-TYPE
        SYNTAX HwXQoSBa8021pMapCfgInfoEntry
        MAX-ACCESS not-accessible
        STATUS current
        DESCRIPTION
            "Diff-serve domain 8021p map Configuration Information Entry."
        INDEX { hwXQoSBaIndex, hwXQoSBa8021pMapIndex }
        ::= { hwXQoSBa8021pMapCfgInfoTable 1 }

    HwXQoSBa8021pMapCfgInfoEntry ::=
        SEQUENCE { 
            hwXQoSBa8021pMapIndex
                Integer32,
            hwXQoSBa8021pMapCos
                Integer32,
            hwXQoSBa8021pMapColour
                Integer32,
            hwXQoSBa8021pMapPri
                Integer32,
            hwXQoSBa8021pMapRowStatus
                RowStatus
         }

    hwXQoSBa8021pMapIndex OBJECT-TYPE
        SYNTAX Integer32
        MAX-ACCESS read-only
        STATUS current
        DESCRIPTION
            "The value of this object identifies the mapping index.The value starts from 0."
        ::= { hwXQoSBa8021pMapCfgInfoEntry 1 }

    hwXQoSBa8021pMapCos OBJECT-TYPE
        SYNTAX Integer32
        MAX-ACCESS read-only
        STATUS current
        DESCRIPTION
            "The value of this object identifies CoS, that is, the scheduling priority.The value can be any of the following:
CS7(7),CS6(6),EF(5),AF4(4),AF3(3),AF2(2),AF1(1),BE(0)."
        ::= { hwXQoSBa8021pMapCfgInfoEntry 2 }

    hwXQoSBa8021pMapColour OBJECT-TYPE
        SYNTAX Integer32
         MAX-ACCESS read-only
        STATUS current
        DESCRIPTION
            "The value of this object identifies the color of the packet, that is, the discarding priority.The value can be any of the following:Green(0),Yellow(1),Red(2)."
        ::= { hwXQoSBa8021pMapCfgInfoEntry 3 }

    hwXQoSBa8021pMapPri OBJECT-TYPE
        SYNTAX Integer32
        MAX-ACCESS read-write
        STATUS current
        DESCRIPTION
            "The value of this object identifies the 8021.p priority.The value ranges from 0 to 7.The object has no default value."
        ::= { hwXQoSBa8021pMapCfgInfoEntry 4 }

    hwXQoSBa8021pMapRowStatus OBJECT-TYPE
        SYNTAX RowStatus
        MAX-ACCESS read-create
        STATUS current
        DESCRIPTION
            "The value of this object identifies the row status.The value can be any of the following:CreateAndGo(4),Destroy(6),Active(1).The object has no default value."
        ::= { hwXQoSBa8021pMapCfgInfoEntry 5 }

--    Dscp-inbound in diff domain        
    hwXQoSBaDscpPhbCfgInfoTable OBJECT-TYPE
        SYNTAX SEQUENCE OF HwXQoSBaDscpPhbCfgInfoEntry
        MAX-ACCESS not-accessible
        STATUS current
        DESCRIPTION
            "A table of diff-serve domain DSCP phb configuration information."
        ::= { hwXQoSBaObjects 4 }

    hwXQoSBaDscpPhbCfgInfoEntry OBJECT-TYPE
        SYNTAX HwXQoSBaDscpPhbCfgInfoEntry
        MAX-ACCESS not-accessible
        STATUS current
        DESCRIPTION
            "Diff-serve domain DSCP phb Configuration Information Entry."
        INDEX { hwXQoSBaIndex, hwXQoSBaDscpPhbIndex }
        ::= { hwXQoSBaDscpPhbCfgInfoTable 1 }

    HwXQoSBaDscpPhbCfgInfoEntry ::=
        SEQUENCE { 
            hwXQoSBaDscpPhbIndex
                Integer32,
            hwXQoSBaDscpPhbPri
                Integer32,
            hwXQoSBaDscpPhbCos
                Integer32,
            hwXQoSBaDscpPhbColour
                Integer32,
            hwXQoSBaDscpPhbRowStatus
                RowStatus
         }

    hwXQoSBaDscpPhbIndex OBJECT-TYPE
        SYNTAX Integer32
        MAX-ACCESS read-only
        STATUS current
        DESCRIPTION
             "The value of this object identifies the index of the Per-Hop Behavior (PHB)."
        ::= { hwXQoSBaDscpPhbCfgInfoEntry 1 }

    hwXQoSBaDscpPhbPri OBJECT-TYPE
        SYNTAX Integer32
        MAX-ACCESS read-only
        STATUS current
        DESCRIPTION
            "The value of this object identifies the priority of DSCP.The value ranges from 0 to 7."
        ::= { hwXQoSBaDscpPhbCfgInfoEntry 2 }

    hwXQoSBaDscpPhbCos OBJECT-TYPE
        SYNTAX Integer32
        MAX-ACCESS read-write
        STATUS current
        DESCRIPTION
            "The value of this object identifies CoS, that is, the scheduling priority.The value can be any of the following:
CS(7),CS(6),EF(5),AF(4),AF(3),AF(2),AF(1),BE(0)."
        ::= { hwXQoSBaDscpPhbCfgInfoEntry 3 }

    
    hwXQoSBaDscpPhbColour OBJECT-TYPE
        SYNTAX Integer32
        MAX-ACCESS read-write
        STATUS current
        DESCRIPTION
            "The value of this object identifies the color of the packet, that is, the discarding priority.The value can be any of the following:Green(0),Yellow(1),Red(2)."
        ::= { hwXQoSBaDscpPhbCfgInfoEntry 4 }

    
    hwXQoSBaDscpPhbRowStatus OBJECT-TYPE
        SYNTAX RowStatus
        MAX-ACCESS read-create
        STATUS current
        DESCRIPTION
            "The value of this object identifies the row status.The value can be any of the following:CreateAndGo(4),Destroy(6),Active(1)."
        ::= { hwXQoSBaDscpPhbCfgInfoEntry 5 }

    
--    Dscp-outbound in diff domain        
    hwXQoSBaDscpMapCfgInfoTable OBJECT-TYPE
        SYNTAX SEQUENCE OF HwXQoSBaDscpMapCfgInfoEntry
        MAX-ACCESS not-accessible
        STATUS current
        DESCRIPTION
            "A table of diff-serve domain Dscp map configuration information."
        ::= { hwXQoSBaObjects 5 }

    
    hwXQoSBaDscpMapCfgInfoEntry OBJECT-TYPE
        SYNTAX HwXQoSBaDscpMapCfgInfoEntry
        MAX-ACCESS not-accessible
        STATUS current
        DESCRIPTION
            "Diff-serve domain Dscp map Configuration Information Entry."
        INDEX { hwXQoSBaIndex, hwXQoSBaDscpMapIndex }
        ::= { hwXQoSBaDscpMapCfgInfoTable 1 }

    
    HwXQoSBaDscpMapCfgInfoEntry ::=
        SEQUENCE { 
            hwXQoSBaDscpMapIndex
                Integer32,
            hwXQoSBaDscpMapCos
                Integer32,
            hwXQoSBaDscpMapColour
                Integer32,
            hwXQoSBaDscpMapPri
                Integer32,
            hwXQoSBaDscpMapRowStatus
                RowStatus
         }

    hwXQoSBaDscpMapIndex OBJECT-TYPE
        SYNTAX Integer32
        MAX-ACCESS read-only
        STATUS current
        DESCRIPTION
            "The value of this object identifies the mapping index."
        ::= { hwXQoSBaDscpMapCfgInfoEntry 1 }

    
    hwXQoSBaDscpMapCos OBJECT-TYPE
        SYNTAX Integer32
        MAX-ACCESS read-only
        STATUS current
        DESCRIPTION
            "The value of this object identifies CoS, that is, the scheduling priority.The value can be any of the following:
CS7(7),CS6(6),EF(5),AF4(4),AF3(3),AF2(2),AF1(1),BE(0)."
        ::= { hwXQoSBaDscpMapCfgInfoEntry 2 }

    
    hwXQoSBaDscpMapColour OBJECT-TYPE
        SYNTAX Integer32
        MAX-ACCESS read-only
        STATUS current
        DESCRIPTION
            "The value of this object identifies the color of the packet, that is, the discarding priority.The value can be any of the following:Green(0),Yellow(1),Red(2)."
        ::= { hwXQoSBaDscpMapCfgInfoEntry 3 }

    
    hwXQoSBaDscpMapPri OBJECT-TYPE
        SYNTAX Integer32
        MAX-ACCESS read-write
        STATUS current
        DESCRIPTION
            "The value of this object identifies the DSCP value.The value ranges from 0 to 7."
        ::= { hwXQoSBaDscpMapCfgInfoEntry 4 }

    
    hwXQoSBaDscpMapRowStatus OBJECT-TYPE
        SYNTAX RowStatus
        MAX-ACCESS read-create
        STATUS current
        DESCRIPTION
            "The value of this object identifies the row status.The value can be any of the following:CreateAndGo(4),Destroy(6),Active(1)."
        ::= { hwXQoSBaDscpMapCfgInfoEntry 5 }

    
--    Exp-inbound in diff domain        
    hwXQoSBaExpPhbCfgInfoTable OBJECT-TYPE
        SYNTAX SEQUENCE OF HwXQoSBaExpPhbCfgInfoEntry
        MAX-ACCESS not-accessible
        STATUS current
        DESCRIPTION
            "A table of diff-serve domain Exp phb configuration information."
        ::= { hwXQoSBaObjects 6 }

    
    hwXQoSBaExpPhbCfgInfoEntry OBJECT-TYPE
        SYNTAX HwXQoSBaExpPhbCfgInfoEntry
        MAX-ACCESS not-accessible
        STATUS current
        DESCRIPTION
            "Diff-serve domain Exp phb Configuration Information Entry."
        INDEX { hwXQoSBaIndex, hwXQoSBaExpPhbIndex }
        ::= { hwXQoSBaExpPhbCfgInfoTable 1 }

    
    HwXQoSBaExpPhbCfgInfoEntry ::=
        SEQUENCE { 
            hwXQoSBaExpPhbIndex
                Integer32,
            hwXQoSBaExpPhbPri
                Integer32,
            hwXQoSBaExpPhbCos
                Integer32,
            hwXQoSBaExpPhbColour
                Integer32,
            hwXQoSBaExpPhbRowStatus
                RowStatus
         }

    hwXQoSBaExpPhbIndex OBJECT-TYPE
        SYNTAX Integer32
        MAX-ACCESS read-only
        STATUS current
        DESCRIPTION
            "The value of this object identifies the index of PHB."
        ::= { hwXQoSBaExpPhbCfgInfoEntry 1 }

    
    hwXQoSBaExpPhbPri OBJECT-TYPE
        SYNTAX Integer32
        MAX-ACCESS read-only
        STATUS current
        DESCRIPTION
            "The value of this object identifies the EXP field of an MPLS packet.The value ranges from 0 to 7."
        ::= { hwXQoSBaExpPhbCfgInfoEntry 2 }

    
    hwXQoSBaExpPhbCos OBJECT-TYPE
        SYNTAX Integer32
        MAX-ACCESS read-write
        STATUS current
        DESCRIPTION
            "The value of this object identifies CoS, that is, the scheduling priority.The value can be any of the following:
CS7(7),CS6(6),EF(5),AF4(4),AF3(3),AF2(2),AF1(1),BE(0)."
        ::= { hwXQoSBaExpPhbCfgInfoEntry 3 }

    
    hwXQoSBaExpPhbColour OBJECT-TYPE
        SYNTAX Integer32
        MAX-ACCESS read-write
        STATUS current
        DESCRIPTION
             "The value of this object identifies the color of the packet, that is, the discarding priority.The value can be any of the following:Green(0),Yellow(1),Red(2)."
        ::= { hwXQoSBaExpPhbCfgInfoEntry 4 }

    
    hwXQoSBaExpPhbRowStatus OBJECT-TYPE
        SYNTAX RowStatus
        MAX-ACCESS read-create
        STATUS current
        DESCRIPTION
            "The value of this object identifies the row status.The value can be any of the following:CreateAndGo(4),Destroy(6),Active(1)."
        ::= { hwXQoSBaExpPhbCfgInfoEntry 5 }

    
--    Exp-outbound in diff domain        
    hwXQoSBaExpMapCfgInfoTable OBJECT-TYPE
        SYNTAX SEQUENCE OF HwXQoSBaExpMapCfgInfoEntry
        MAX-ACCESS not-accessible
        STATUS current
        DESCRIPTION
            "A table of diff-serve domain Exp map configuration information."
        ::= { hwXQoSBaObjects 7 }

    
    hwXQoSBaExpMapCfgInfoEntry OBJECT-TYPE
        SYNTAX HwXQoSBaExpMapCfgInfoEntry
        MAX-ACCESS not-accessible
        STATUS current
        DESCRIPTION
            "Diff-serve domain Exp map Configuration Information Entry."
        INDEX { hwXQoSBaIndex, hwXQoSBaExpMapIndex }
        ::= { hwXQoSBaExpMapCfgInfoTable 1 }

    
    HwXQoSBaExpMapCfgInfoEntry ::=
        SEQUENCE { 
            hwXQoSBaExpMapIndex
                Integer32,
            hwXQoSBaExpMapCos
                Integer32,
            hwXQoSBaExpMapColour
                Integer32,
            hwXQoSBaExpMapPri
                Integer32,
            hwXQoSBaExpMapRowStatus
                RowStatus
         }

    hwXQoSBaExpMapIndex OBJECT-TYPE
        SYNTAX Integer32
        MAX-ACCESS read-only
        STATUS current
        DESCRIPTION
            "The value of this object identifies the mapping index."
        ::= { hwXQoSBaExpMapCfgInfoEntry 1 }

    
    hwXQoSBaExpMapCos OBJECT-TYPE
        SYNTAX Integer32
        MAX-ACCESS read-only
        STATUS current
        DESCRIPTION
             "The value of this object identifies CoS, that is, the scheduling priority.The value can be any of the following:CS7(7),CS6(6),EF(5),AF4(4),AF3(3),AF2(2),AF1(1),BE(0)."
        ::= { hwXQoSBaExpMapCfgInfoEntry 2 }

    
    hwXQoSBaExpMapColour OBJECT-TYPE
        SYNTAX Integer32
        MAX-ACCESS read-only
        STATUS current
        DESCRIPTION
            "The value of this object identifies the color of the packet, that is, the discarding priority.The value can be any of the following:Green(0),Yellow(1),Red(2)."
        ::= { hwXQoSBaExpMapCfgInfoEntry 3 }

    
    hwXQoSBaExpMapPri OBJECT-TYPE
        SYNTAX Integer32
        MAX-ACCESS read-write
        STATUS current
        DESCRIPTION
            "The value of this object identifies the EXP field of the MPLS packet.The value ranges from 0 to 7."
        ::= { hwXQoSBaExpMapCfgInfoEntry 4 }

    
    hwXQoSBaExpMapRowStatus OBJECT-TYPE
        SYNTAX RowStatus
        MAX-ACCESS read-create
        STATUS current
        DESCRIPTION
            "The value of this object identifies the row status.The value can be any of the following:CreateAndGo(4),Destroy(6),Active(1)."
        ::= { hwXQoSBaExpMapCfgInfoEntry 5 }

    
--    trust upstream
    hwXQoSIfDiffDomainTable OBJECT-TYPE
        SYNTAX SEQUENCE OF HwXQoSIfDiffDomainEntry
        MAX-ACCESS not-accessible
        STATUS current
        DESCRIPTION
            "Trust diff-serve domain."
        ::= { hwXQoSBaObjects 8 }

    
    hwXQoSIfDiffDomainEntry OBJECT-TYPE
        SYNTAX HwXQoSIfDiffDomainEntry
        MAX-ACCESS not-accessible
        STATUS current
        DESCRIPTION
            "Policy applied on interface Configuration Information Entry."
        INDEX { hwXQoSIfDiffDomainIfIndex, hwXQoSIfDiffDomainVlanId }
        ::= { hwXQoSIfDiffDomainTable 1 }

    
    HwXQoSIfDiffDomainEntry ::=
        SEQUENCE { 
            hwXQoSIfDiffDomainIfIndex
                Integer32, 
            hwXQoSIfDiffDomainVlanId
                Integer32,  
            hwXQoSIfDiffDomainName
                OCTET STRING,
            hwXQoSIfDiffDomainRowStatus
                RowStatus,      
            hwXQoSIfDiffDomainVlanId2
                Integer32
         }

    hwXQoSIfDiffDomainIfIndex OBJECT-TYPE
        SYNTAX Integer32
        MAX-ACCESS read-only
        STATUS current
        DESCRIPTION
            "The value of this object identifies the interface index."
        ::= { hwXQoSIfDiffDomainEntry 1 }

    hwXQoSIfDiffDomainVlanId OBJECT-TYPE
        SYNTAX Integer32 (0 | 1..4094)
        MAX-ACCESS read-only
        STATUS current
        DESCRIPTION
            "The value of this object identifies the VLAN ID of the interface."
        ::= { hwXQoSIfDiffDomainEntry 2 }

    hwXQoSIfDiffDomainName OBJECT-TYPE
        SYNTAX OCTET STRING (SIZE (1..31))
        MAX-ACCESS read-create
        STATUS current
        DESCRIPTION
            "This object indicates the name of the DS domain.The value of the object ranges from 1 to 31.The name cannot contain Chinese characters."
        ::= { hwXQoSIfDiffDomainEntry 3 }

    
    hwXQoSIfDiffDomainRowStatus OBJECT-TYPE
        SYNTAX RowStatus
        MAX-ACCESS read-create
        STATUS current
        DESCRIPTION
            "This value of this object identifies the row status.The value can be any of the following:CreateAndGo(4), Destroy(6),Active(1)."
        ::= { hwXQoSIfDiffDomainEntry 4 }

  
        
    hwXQoSIfDiffDomainVlanId2 OBJECT-TYPE
        SYNTAX Integer32 (0 | 1..4094)
        MAX-ACCESS read-create
        STATUS current
        DESCRIPTION
            "End vlan ID.
            -1 can't be set.
            0 is the default value"
        ::= { hwXQoSIfDiffDomainEntry 5 }

    
--    trust 8021p
    hwXQoSIfTrust8021pTable OBJECT-TYPE
        SYNTAX SEQUENCE OF HwXQoSIfTrust8021pEntry
        MAX-ACCESS not-accessible
        STATUS current
        DESCRIPTION
            "Trust diff-serve domain."
        ::= { hwXQoSBaObjects 9 }

    
    hwXQoSIfTrust8021pEntry OBJECT-TYPE
        SYNTAX HwXQoSIfTrust8021pEntry
        MAX-ACCESS not-accessible
        STATUS current
        DESCRIPTION
            "Policy applied on interface Configuration Information Entry."
        INDEX { hwXQoSIfTrust8021pIfIndex, hwXQoSIfTrust8021pVlanID }
        ::= { hwXQoSIfTrust8021pTable 1 }

    
    HwXQoSIfTrust8021pEntry ::=
        SEQUENCE { 
            hwXQoSIfTrust8021pIfIndex
                Integer32,
            hwXQoSIfTrust8021pVlanID
                Integer32,
            hwXQoSIfTrust8021pAction
                INTEGER,
            hwXQoSIfTrust8021pRowStatus
                RowStatus
         }

    hwXQoSIfTrust8021pIfIndex OBJECT-TYPE
        SYNTAX Integer32
        MAX-ACCESS read-only
        STATUS current
        DESCRIPTION
            "The value of this object identifies the interface index."
        ::= { hwXQoSIfTrust8021pEntry 1 }

    hwXQoSIfTrust8021pVlanID OBJECT-TYPE
        SYNTAX Integer32 (0 | 1..4094)
        MAX-ACCESS read-only
        STATUS current
        DESCRIPTION
            "The value of this object identifies the VLAN ID of the interface."
        ::= { hwXQoSIfTrust8021pEntry 2 }
 
     hwXQoSIfTrust8021pAction OBJECT-TYPE
        SYNTAX INTEGER {
            distrust(1),
            trust(2)
           }
        MAX-ACCESS read-create
        STATUS current
        DESCRIPTION
            "The value of this object identifies whether the Layer 2 simple stream classification is enabled.The value can be either of the following:Distrust(1),Trust(2).The object has no default value."
        ::= { hwXQoSIfTrust8021pEntry 3 }  
        
    hwXQoSIfTrust8021pRowStatus OBJECT-TYPE
        SYNTAX RowStatus
        MAX-ACCESS read-create
        STATUS current
        DESCRIPTION
            "This value of this object identifies the row status.The value can be any of the following:CreateAndGo(4),
Destroy(6),Active(1).The object has no default value."
        ::= { hwXQoSIfTrust8021pEntry 4 }

-- Atm Qos ServiceType+Clp to Cos+Color in diff domain                                                           
   hwXQoSBaAtmQosPhbCfgInfoTable OBJECT-TYPE                                                                     
        SYNTAX SEQUENCE OF HwXQoSBaAtmQosPhbCfgInfoEntry                                                         
        MAX-ACCESS not-accessible                                                                                
        STATUS current                                                                                           
        DESCRIPTION                                                                                              
            "A table of diff-serve domain AtmQos ServiceType+Clp phb configuration information."                 
        ::= { hwXQoSBaObjects 10 }                                                                               
                                                                                                                 
    hwXQoSBaAtmQosPhbCfgInfoEntry OBJECT-TYPE                                                                    
        SYNTAX HwXQoSBaAtmQosPhbCfgInfoEntry                                                                     
        MAX-ACCESS not-accessible                                                                                
        STATUS current                                                                                           
        DESCRIPTION                                                                                              
            "Diff-serve domain AtmQos ServiceType+Clp phb Configuration Information Entry."                      
        INDEX { hwXQoSBaIndex, hwXQoSBaAtmQosPhbServType, hwXQoSBaAtmQosPhbClp  }                                
        ::= { hwXQoSBaAtmQosPhbCfgInfoTable 1 }                                                                  
                                                                                                                 
    HwXQoSBaAtmQosPhbCfgInfoEntry ::=                                                                            
        SEQUENCE {                                                                                               
            hwXQoSBaAtmQosPhbServType                                                                            
                Integer32,                                                                                       
            hwXQoSBaAtmQosPhbClp                                                                                 
                Integer32,                                                                                       
            hwXQoSBaAtmQosPhbCos                                                                                 
                Integer32,                                                                                       
            hwXQoSBaAtmQosPhbColour                                                                              
                Integer32,                                                                                       
            hwXQoSBaAtmQosPhbRowStatus                                                                           
                RowStatus                                                                                        
         }                                                                                                       
                                                                                                                 
    hwXQoSBaAtmQosPhbServType OBJECT-TYPE                                                                        
        SYNTAX Integer32                                                                                         
        MAX-ACCESS read-only                                                                                     
        STATUS current                                                                                           
        DESCRIPTION                                                                                              
            "Atm Qos ServiceType."                                                                               
        ::= { hwXQoSBaAtmQosPhbCfgInfoEntry 1 }                                                                  
                                                                                                                 
    hwXQoSBaAtmQosPhbClp OBJECT-TYPE                                                                             
        SYNTAX Integer32                                                                                         
        MAX-ACCESS read-only                                                                                     
        STATUS current                                                                                           
        DESCRIPTION                                                                                              
            "Atm Qos Clp."                                                                                       
        ::= { hwXQoSBaAtmQosPhbCfgInfoEntry 2 }                                                                  
                                                                                                                 
    hwXQoSBaAtmQosPhbCos OBJECT-TYPE                                                                             
        SYNTAX Integer32                                                                                         
        MAX-ACCESS read-write                                                                                    
        STATUS current                                                                                           
        DESCRIPTION                                                                                              
            "Cos of AtmQos."                                                                                     
        ::= { hwXQoSBaAtmQosPhbCfgInfoEntry 3 }                                                                  
                                                                                                                 
    hwXQoSBaAtmQosPhbColour OBJECT-TYPE                                                                          
        SYNTAX Integer32                                                                                         
        MAX-ACCESS read-write                                                                                    
        STATUS current                                                                                           
        DESCRIPTION                                                                                              
            "Colour of AtmQos."                                                                                  
        ::= { hwXQoSBaAtmQosPhbCfgInfoEntry 4 }                                                                  
                                                                                                                 
    hwXQoSBaAtmQosPhbRowStatus OBJECT-TYPE                                                                       
        SYNTAX RowStatus                                                                                         
        MAX-ACCESS read-create                                                                                   
        STATUS current                                                                                           
        DESCRIPTION                                                                                              
            "RowStatus. Three actions are used: active,                                                          
            createAndGo, destroy"                                                                                
        ::= { hwXQoSBaAtmQosPhbCfgInfoEntry 5 }                                                                  
                                                                                                                 
--    Atm Qos Cos+Color to Clp in diff domain                                                                 
    hwXQoSBaAtmQosMapCfgInfoTable OBJECT-TYPE                                                                    
        SYNTAX SEQUENCE OF HwXQoSBaAtmQosMapCfgInfoEntry                                                         
        MAX-ACCESS not-accessible                                                                                
        STATUS current                                                                                           
        DESCRIPTION                                                                                              
            "A table of diff-serve domain Atm Qos Clp map configuration information."                            
        ::= { hwXQoSBaObjects 11 }                                                                               
                                                                                                                 
    hwXQoSBaAtmQosMapCfgInfoEntry OBJECT-TYPE                                                                    
        SYNTAX HwXQoSBaAtmQosMapCfgInfoEntry                                                                     
        MAX-ACCESS not-accessible                                                                                
        STATUS current                                                                                           
        DESCRIPTION                                                                                              
            "Diff-serve domain Atm Qos Clp map Configuration Information Entry."                                 
        INDEX { hwXQoSBaIndex, hwXQoSBaAtmQosMapIndex}                                                           
        ::= { hwXQoSBaAtmQosMapCfgInfoTable 1 }                                                                  
                                                                                                                 
    HwXQoSBaAtmQosMapCfgInfoEntry ::=                                                                            
        SEQUENCE {                                                                                               
            hwXQoSBaAtmQosMapIndex                                                                               
                Integer32,                                                                                       
            hwXQoSBaAtmQosMapCos                                                                                 
                Integer32,                                                                                       
            hwXQoSBaAtmQosMapColour                                                                              
                Integer32,                                                                                       
            hwXQoSBaAtmQosMapClp                                                                                 
                Integer32,                                                                                       
            hwXQoSBaAtmQosMapRowStatus                                                                           
                RowStatus                                                                                        
         }                                                                                                       
                                                                                                                 
                                                                                                                 
     hwXQoSBaAtmQosMapIndex OBJECT-TYPE                                                                          
        SYNTAX Integer32                                                                                         
        MAX-ACCESS read-only                                                                                     
        STATUS current                                                                                           
        DESCRIPTION                                                                                              
            "Atm Qos index in diff-serve domain."                                                                
        ::= { hwXQoSBaAtmQosMapCfgInfoEntry 1 }                                                                  
                                                                                                                 
    hwXQoSBaAtmQosMapCos OBJECT-TYPE                                                                             
        SYNTAX Integer32                                                                                         
        MAX-ACCESS read-only                                                                                     
        STATUS current                                                                                           
        DESCRIPTION                                                                                              
            "Cos of AtmQos."                                                                                     
        ::= { hwXQoSBaAtmQosMapCfgInfoEntry 2 }                                                                  
                                                                                                                 
    hwXQoSBaAtmQosMapColour OBJECT-TYPE                                                                          
        SYNTAX Integer32                                                                                         
         MAX-ACCESS read-only                                                                                    
        STATUS current                                                                                           
        DESCRIPTION                                                                                              
            "Colour of AtmQos."                                                                                  
        ::= { hwXQoSBaAtmQosMapCfgInfoEntry 3 }                                                                  
                                                                                                                 
    hwXQoSBaAtmQosMapClp OBJECT-TYPE                                                                             
        SYNTAX Integer32                                                                                         
        MAX-ACCESS read-write                                                                                    
        STATUS current                                                                                           
        DESCRIPTION                                                                                              
            "AtmQos Clp."                                                                                        
        ::= { hwXQoSBaAtmQosMapCfgInfoEntry 4 }                                                                  
                                                                                                                 
    hwXQoSBaAtmQosMapRowStatus OBJECT-TYPE                                                                       
        SYNTAX RowStatus                                                                                         
        MAX-ACCESS read-create                                                                                   
        STATUS current                                                                                           
        DESCRIPTION                                                                                              
            "RowStatus. Three actions are used: active,                                                          
            createAndGo, destroy"                                                                                
        ::= { hwXQoSBaAtmQosMapCfgInfoEntry 5 }                                                                  
                                                                                                                 
--    trust upstream on atm pvc                                                                                  
    hwXQoSAtmPvcDiffDomainTable OBJECT-TYPE                                                                      
        SYNTAX SEQUENCE OF HwXQoSAtmPvcDiffDomainEntry                                                           
        MAX-ACCESS not-accessible                                                                                
        STATUS current                                                                                           
        DESCRIPTION                                                                                              
            "Trust diff-serve domain."                                                                           
        ::= { hwXQoSBaObjects 12 }                                                                               
                                                                                                                 
    hwXQoSAtmPvcDiffDomainEntry OBJECT-TYPE                                                                      
        SYNTAX HwXQoSAtmPvcDiffDomainEntry                                                                       
        MAX-ACCESS not-accessible                                                                                
        STATUS current                                                                                           
        DESCRIPTION                                                                                              
            "Policy applied on pvc interface Configuration Information Entry."                                   
        INDEX { hwXQoSAtmPvcDiffDomainIfIndex, hwXQoSAtmPvcVpi, hwXQoSAtmPvcVci}                                 
        ::= { hwXQoSAtmPvcDiffDomainTable 1 }                                                                    
                                                                                                                 
    HwXQoSAtmPvcDiffDomainEntry ::=                                                                              
        SEQUENCE {                                                                                               
            hwXQoSAtmPvcDiffDomainIfIndex                                                                        
                Integer32,                                                                                       
            hwXQoSAtmPvcVpi                                                                                      
                Integer32,                                                                                       
            hwXQoSAtmPvcVci                                                                                      
                Integer32,                                                                                       
            hwXQoSAtmPvcDiffDomainName                                                                           
                OCTET STRING,                                                                                    
            hwXQoSAtmPvcDiffDomainRowStatus                                                                      
                RowStatus                                                                                        
         }                                                                                                       
                                                                                                                 
    hwXQoSAtmPvcDiffDomainIfIndex OBJECT-TYPE                                                                    
        SYNTAX Integer32                                                                                         
        MAX-ACCESS read-only                                                                                     
        STATUS current                                                                                           
        DESCRIPTION                                                                                              
            "Atm Interface Index."                                                                               
        ::= { hwXQoSAtmPvcDiffDomainEntry 1 }                                                                    
                                                                                                                 
    hwXQoSAtmPvcVpi OBJECT-TYPE                                                                                  
        SYNTAX Integer32                                                                                         
        MAX-ACCESS read-only                                                                                     
        STATUS current                                                                                           
        DESCRIPTION                                                                                              
            "Atm Pvc Vpi"                                                                                        
        ::= { hwXQoSAtmPvcDiffDomainEntry 2 }                                                                    
                                                                                                                 
    hwXQoSAtmPvcVci OBJECT-TYPE                                                                                  
        SYNTAX Integer32                                                                                         
        MAX-ACCESS read-only                                                                                     
        STATUS current                                                                                           
        DESCRIPTION                                                                                              
            "Atm Pvc Vci"                                                                                        
        ::= { hwXQoSAtmPvcDiffDomainEntry 3 }                                                                    
                                                                                                                 
    hwXQoSAtmPvcDiffDomainName OBJECT-TYPE                                                                       
        SYNTAX OCTET STRING (SIZE (1..31))                                                                       
        MAX-ACCESS read-create                                                                                   
        STATUS current                                                                                           
        DESCRIPTION                                                                                              
            "Name of diff-serve domain."                                                                         
        ::= { hwXQoSAtmPvcDiffDomainEntry 4 }                                                                    
                                                                                                                 
    hwXQoSAtmPvcDiffDomainRowStatus OBJECT-TYPE                                                                  
        SYNTAX RowStatus                                                                                         
        MAX-ACCESS read-create                                                                                   
        STATUS current                                                                                           
        DESCRIPTION                                                                                              
            "RowStatus. Three actions are used: active,                                                          
            createAndGo, destroy"                                                                                
        ::= { hwXQoSAtmPvcDiffDomainEntry 5 }                                                                    
                                                                                                                 
--    trust upstream on atm pvp                                                                                  
  hwXQoSAtmPvpDiffDomainTable OBJECT-TYPE                                                                        
        SYNTAX SEQUENCE OF HwXQoSAtmPvpDiffDomainEntry                                                           
        MAX-ACCESS not-accessible                                                                                
        STATUS current                                                                                           
        DESCRIPTION                                                                                              
            "Trust diff-serve domain."                                                                           
        ::= { hwXQoSBaObjects 13 }                                                                               
                                                                                                                 
    hwXQoSAtmPvpDiffDomainEntry OBJECT-TYPE                                                                      
        SYNTAX HwXQoSAtmPvpDiffDomainEntry                                                                       
        MAX-ACCESS not-accessible                                                                                
        STATUS current                                                                                           
        DESCRIPTION                                                                                              
            "Policy applied on pvp interface Configuration Information Entry."                                   
        INDEX { hwXQoSAtmPvpDiffDomainIfIndex, hwXQoSAtmPvpVpi}                                                  
        ::= { hwXQoSAtmPvpDiffDomainTable 1 }                                                                    
                                                                                                                 
    HwXQoSAtmPvpDiffDomainEntry ::=                                                                              
        SEQUENCE {                                                                                               
            hwXQoSAtmPvpDiffDomainIfIndex                                                                        
                Integer32,                                                                                       
            hwXQoSAtmPvpVpi                                                                                      
                Integer32,                                                                                       
            hwXQoSAtmPvpDiffDomainName                                                                           
                OCTET STRING,                                                                                    
            hwXQoSAtmPvpDiffDomainRowStatus                                                                      
                RowStatus                                                                                        
         }                                                                                                       
                                                                                                                 
    hwXQoSAtmPvpDiffDomainIfIndex OBJECT-TYPE                                                                    
        SYNTAX Integer32                                                                                         
        MAX-ACCESS read-only                                                                                     
        STATUS current                                                                                           
        DESCRIPTION                                                                                              
            "Atm Interface Index."                                                                               
        ::= { hwXQoSAtmPvpDiffDomainEntry 1 }                                                                    
                                                                                                                 
    hwXQoSAtmPvpVpi OBJECT-TYPE                                                                                  
        SYNTAX Integer32                                                                                         
        MAX-ACCESS read-only                                                                                     
        STATUS current                                                                                           
        DESCRIPTION                                                                                              
            "Atm Pvp Vpi"                                                                                        
        ::= { hwXQoSAtmPvpDiffDomainEntry 2 }                                                                    
                                                                                                                 
    hwXQoSAtmPvpDiffDomainName OBJECT-TYPE                                                                       
        SYNTAX OCTET STRING (SIZE (1..31))                                                                       
        MAX-ACCESS read-create                                                                                   
        STATUS current                                                                                           
        DESCRIPTION                                                                                              
            "Name of diff-serve domain."                                                                         
        ::= { hwXQoSAtmPvpDiffDomainEntry 3 }                                                                    
                                                                                                                 
    hwXQoSAtmPvpDiffDomainRowStatus OBJECT-TYPE                                                                  
        SYNTAX RowStatus                                                                                         
        MAX-ACCESS read-create                                                                                   
        STATUS current                                                                                           
        DESCRIPTION                                                                                              
            "RowStatus. Three actions are used: active,                                                          
            createAndGo, destroy"                                                                                
        ::= { hwXQoSAtmPvpDiffDomainEntry 4 }                                                                    



        -- inbound in diff domain
        hwXQoSBaPhbCfgInfoTable OBJECT-TYPE
            SYNTAX SEQUENCE OF HwXQoSBaPhbCfgInfoEntry
            MAX-ACCESS not-accessible
            STATUS current
            DESCRIPTION
                "A table of diff-serve domain 8021p/Dscp/Exp/IpPri/hqosVlan8021p/hqosDscp/hqosMplsExp/hqosIpPri phb configuration information."
            ::= { hwXQoSBaObjects 14 }
        
        hwXQoSBaPhbCfgInfoEntry OBJECT-TYPE
            SYNTAX HwXQoSBaPhbCfgInfoEntry
            MAX-ACCESS not-accessible
            STATUS current
            DESCRIPTION
                "Diff-serve domain 8021p/Dscp/Exp/IpPri/hqosVlan8021p/hqosDscp/hqosMplsExp/hqosIpPri phb Configuration Information Entry."
            INDEX { hwXQoSBaIndex,hwXQoSBaPhbType,hwXQoSBaPhbPri }
            ::= { hwXQoSBaPhbCfgInfoTable 1 }
        
        HwXQoSBaPhbCfgInfoEntry ::=
            SEQUENCE { 
                hwXQoSBaPhbType
                    BaType,
                hwXQoSBaPhbPri
                    Integer32,
                hwXQoSBaPhbCos
                    Integer32,
                hwXQoSBaPhbColour
                    INTEGER,
                hwXQoSBaPhbRowStatus
                    RowStatus
             }
        
        
        hwXQoSBaPhbType OBJECT-TYPE
            SYNTAX BaType
            MAX-ACCESS not-accessible
            STATUS current
            DESCRIPTION
                " 8021p (1),
                dscp (2),
                mplsExp(3),
                ipPri(4),
                hqosVlan8021p(5),
                hqosDscp(6),
                hqosMplsExp(7),
                hqosIpPri(8),
                vlan8021pInbound(9)."

            ::= { hwXQoSBaPhbCfgInfoEntry 1 }
        
        hwXQoSBaPhbPri OBJECT-TYPE
            SYNTAX Integer32
            MAX-ACCESS not-accessible
            STATUS current
            DESCRIPTION
                "8021p / Dscp/Exp / IpPri / hqosVlan8021p / hqosDscp / hqosMplsExp / hqosIpPri."
            ::= { hwXQoSBaPhbCfgInfoEntry 2 }
        
        hwXQoSBaPhbCos OBJECT-TYPE
            SYNTAX Integer32
            MAX-ACCESS read-create
            STATUS current
            DESCRIPTION
                "Cos of 8021p / Dscp / Exp / IpPri / hqosVlan8021p / hqosDscp / hqosMplsExp / hqosIpPri."
            ::= { hwXQoSBaPhbCfgInfoEntry 3 }
        
        hwXQoSBaPhbColour OBJECT-TYPE
            SYNTAX INTEGER
            {    
             green(1),
             yellow(2),
             red(3)
            }
            MAX-ACCESS read-create
            STATUS current
            DESCRIPTION
                "Colour of 8021p/Dscp/Exp/IpPri/hqosVlan8021p/hqosDscp/hqosMplsExp/hqosIpPri."
            ::= { hwXQoSBaPhbCfgInfoEntry 4 }
        
        hwXQoSBaPhbRowStatus OBJECT-TYPE
            SYNTAX RowStatus
            MAX-ACCESS read-create
            STATUS current
            DESCRIPTION
                "RowStatus. Three actions are used: active,
                createAndGo, destroy"
            ::= { hwXQoSBaPhbCfgInfoEntry 5 }


        -- outbound in diff domain
        hwXQoSBaMapCfgInfoTable OBJECT-TYPE
            SYNTAX SEQUENCE OF HwXQoSBaMapCfgInfoEntry
            MAX-ACCESS not-accessible
            STATUS current
            DESCRIPTION
                "A table of diff-serve domain 8021p/Dscp/Exp/IpPri/hqosVlan8021p/hqosDscp/hqosMplsExp/hqosIpPri map configuration information."
            ::= { hwXQoSBaObjects 15 }
        
        hwXQoSBaMapCfgInfoEntry OBJECT-TYPE
            SYNTAX HwXQoSBaMapCfgInfoEntry
            MAX-ACCESS not-accessible
            STATUS current
            DESCRIPTION
                "Diff-serve domain 8021p/Dscp/Exp/IpPri/hqosVlan8021p/hqosDscp/hqosMplsExp/hqosIpPri map Configuration Information Entry."
            INDEX { hwXQoSBaIndex,hwXQoSBaMapType,hwXQoSBaMapCos,hwXQoSBaMapColour }
            ::= { hwXQoSBaMapCfgInfoTable 1 }
        
        HwXQoSBaMapCfgInfoEntry ::=
            SEQUENCE { 

                hwXQoSBaMapType
                    BaType,
                hwXQoSBaMapCos
                    Integer32,
                hwXQoSBaMapColour
                    INTEGER,
                hwXQoSBaMapPri
                    Integer32,
                hwXQoSBaMapRowStatus
                    RowStatus
             }
        
        
        
        hwXQoSBaMapType OBJECT-TYPE
            SYNTAX BaType
            MAX-ACCESS not-accessible
            STATUS current
            DESCRIPTION
                " 8021p (1),
                dscp (2),
                mplsExp(3),
                ipPri(4),
                hqosVlan8021p(5),
                hqosDscp(6),
                hqosMplsExp(7),
                hqosIpPri(8)."
            ::= { hwXQoSBaMapCfgInfoEntry 1 }
        
        hwXQoSBaMapCos OBJECT-TYPE
            SYNTAX Integer32
            MAX-ACCESS not-accessible
            STATUS current
            DESCRIPTION
                "Cos of 8021p/Dscp/Exp/IpPri/hqosVlan8021p/hqosDscp/hqosMplsExp/hqosIpPri."
            ::= { hwXQoSBaMapCfgInfoEntry 2 }
        
        hwXQoSBaMapColour OBJECT-TYPE
            SYNTAX INTEGER 
            {
             green(1),
             yellow(2),
             red(3)
            }
            MAX-ACCESS  not-accessible
            STATUS current
            DESCRIPTION
                "Colour of 8021p/Dscp/Exp/IpPri/hqosVlan8021p/hqosDscp/hqosMplsExp/hqosIpPri."
            ::= { hwXQoSBaMapCfgInfoEntry 3 }
        
        hwXQoSBaMapPri OBJECT-TYPE
            SYNTAX Integer32
            MAX-ACCESS read-create
            STATUS current
            DESCRIPTION
                "8021p/Dscp/Exp/IpPri/hqosVlan8021p/hqosDscp/hqosMplsExp/hqosIpPri."
            ::= { hwXQoSBaMapCfgInfoEntry 4 }
        
        hwXQoSBaMapRowStatus OBJECT-TYPE
            SYNTAX RowStatus
            MAX-ACCESS read-create
            STATUS current
            DESCRIPTION
                "RowStatus. Three actions are used: active,
                createAndGo, destroy"
            ::= { hwXQoSBaMapCfgInfoEntry 5 }


        hwXQoSIfTrustTable OBJECT-TYPE
            SYNTAX SEQUENCE OF HwXQoSIfTrustEntry
            MAX-ACCESS not-accessible
            STATUS current
            DESCRIPTION
                "Trust diff-serve domain."
            ::= { hwXQoSBaObjects 16 }
        
        hwXQoSIfTrustEntry OBJECT-TYPE
            SYNTAX HwXQoSIfTrustEntry
            MAX-ACCESS not-accessible
            STATUS current
            DESCRIPTION
                "Policy applied on interface Configuration Information Entry."
            INDEX { hwXQoSIfTrustIfIndex, hwXQoSIfTrustVlanID1,hwXQoSIfTrustVlanID2,hwXQoSBaType }
            ::= { hwXQoSIfTrustTable 1 }
        
        HwXQoSIfTrustEntry ::=
            SEQUENCE { 
                hwXQoSIfTrustIfIndex
                    Integer32,
                hwXQoSIfTrustVlanID1
                    Integer32,
                hwXQoSIfTrustVlanID2
                    Integer32,
                hwXQoSBaType
                    BaType,
                hwXQoSIfTrustAction
                    INTEGER,
                hwXQoSIfTrustRowStatus
                    RowStatus                
             }
        
        hwXQoSIfTrustIfIndex OBJECT-TYPE
            SYNTAX Integer32
            MAX-ACCESS not-accessible
            STATUS current
            DESCRIPTION
                "Interface Index, equal to ifIndex."
            ::= { hwXQoSIfTrustEntry 1 }
        
        hwXQoSIfTrustVlanID1 OBJECT-TYPE
            SYNTAX Integer32 (0 | 1..4095)
            MAX-ACCESS not-accessible
            STATUS current
            DESCRIPTION
                "start Vlan ID.
                -1 can't be set.
                0 is the default value"
            ::= { hwXQoSIfTrustEntry 2 }
        
        hwXQoSIfTrustVlanID2 OBJECT-TYPE
            SYNTAX Integer32 (0 | 1..4095)
            MAX-ACCESS not-accessible
            STATUS current
            DESCRIPTION
                "end Vlan ID.
                -1 can't be set.
                0 is the default value"
            ::= { hwXQoSIfTrustEntry 3 }
        
        hwXQoSBaType OBJECT-TYPE
            SYNTAX BaType
            MAX-ACCESS not-accessible
            STATUS current
            DESCRIPTION
                "vlan8021p (1),
                dscp (2),
                mplsExp(3),
                ipPri(4)"
            ::= { hwXQoSIfTrustEntry 4 }
            
         hwXQoSIfTrustAction OBJECT-TYPE
            SYNTAX INTEGER {
                distrust(1),
                trust(2)
               }
            MAX-ACCESS read-create
            STATUS current
            DESCRIPTION
                "The trust 802.1p action "
            ::= { hwXQoSIfTrustEntry 5 }  
            
        hwXQoSIfTrustRowStatus OBJECT-TYPE
            SYNTAX RowStatus
            MAX-ACCESS read-create
            STATUS current
            DESCRIPTION
                "RowStatus. Three actions are used: active,
                createAndGo, destroy"
            ::= { hwXQoSIfTrustEntry 6 }


        hwXQoSDeiTable OBJECT-TYPE
            SYNTAX SEQUENCE OF HwXQoSDeiEntry
            MAX-ACCESS not-accessible
            STATUS current
            DESCRIPTION
                "Enable dei."
            ::= { hwXQoSBaObjects 17 }
        
        hwXQoSDeiEntry OBJECT-TYPE
            SYNTAX HwXQoSDeiEntry
            MAX-ACCESS not-accessible
            STATUS current
            DESCRIPTION
                "Policy applied on interface Configuration Information Entry."
            INDEX { hwXQoSDeiIfIndex, hwXQoSDeiVlanID1,hwXQoSDeiVlanID2 }
            ::= { hwXQoSDeiTable 1 }
        
        HwXQoSDeiEntry ::=
            SEQUENCE { 
                hwXQoSDeiIfIndex
                    Integer32,
                hwXQoSDeiVlanID1
                    Integer32,
                hwXQoSDeiVlanID2
                    Integer32,
                hwXQoSIfEnableDeiAction
                    INTEGER,
                hwXQoSDeiRowStatus
                    RowStatus
             }
        
        hwXQoSDeiIfIndex OBJECT-TYPE
            SYNTAX Integer32
            MAX-ACCESS not-accessible
            STATUS current
            DESCRIPTION
                "Interface Index, equal to ifIndex."
            ::= { hwXQoSDeiEntry 1 }
        
        hwXQoSDeiVlanID1 OBJECT-TYPE
            SYNTAX Integer32 (0 | 1..4095)
            MAX-ACCESS not-accessible
            STATUS current
            DESCRIPTION
                "start Vlan ID.
                -1 can't be set.
                0 is the default value"
            ::= { hwXQoSDeiEntry 2 }
        
        hwXQoSDeiVlanID2 OBJECT-TYPE
            SYNTAX Integer32 (0 | 1..4095)
            MAX-ACCESS not-accessible
            STATUS current
            DESCRIPTION
                "end Vlan ID.
                -1 can't be set.
                0 is the default value"
            ::= { hwXQoSDeiEntry 3 }
        
        hwXQoSIfEnableDeiAction OBJECT-TYPE
            SYNTAX INTEGER {
             enabled(1),
             unenabled(2)
            }
            MAX-ACCESS read-create
            STATUS current
            DESCRIPTION
                " The enable dei action 
                enabled(1),
                unenabled(2)"
            ::= { hwXQoSDeiEntry 4 }
        
        hwXQoSDeiRowStatus OBJECT-TYPE
            SYNTAX RowStatus
            MAX-ACCESS read-create
            STATUS current
            DESCRIPTION
                "RowStatus. Three actions are used: active,
                createAndGo, destroy"
            ::= { hwXQoSDeiEntry 5 }

        hwXQoSRemarkTable OBJECT-TYPE
            SYNTAX SEQUENCE OF HwXQoSRemarkEntry
            MAX-ACCESS not-accessible
            STATUS current
            DESCRIPTION
                "Enable Remark."
            ::= { hwXQoSBaObjects 18 }
        
        hwXQoSRemarkEntry OBJECT-TYPE
            SYNTAX HwXQoSRemarkEntry
            MAX-ACCESS not-accessible
            STATUS current
            DESCRIPTION
                "Policy applied on interface Configuration Information Entry."
            INDEX { hwXQoSRemarkIfIndex, hwXQoSRemarkVlanID1,hwXQoSRemarkVlanID2 }
            ::= { hwXQoSRemarkTable 1 }
        
        HwXQoSRemarkEntry ::=
            SEQUENCE { 
                hwXQoSRemarkIfIndex
                    Integer32,
                hwXQoSRemarkVlanID1
                    Integer32,
                hwXQoSRemarkVlanID2
                    Integer32,
                hwXQoSIfEnableRemarkAction
                    INTEGER,
                hwXQoSRemarkRowStatus
                    RowStatus
             }
        
        hwXQoSRemarkIfIndex OBJECT-TYPE
            SYNTAX Integer32
            MAX-ACCESS not-accessible
            STATUS current
            DESCRIPTION
                "Interface Index, equal to ifIndex."
            ::= { hwXQoSRemarkEntry 1 }
        
        hwXQoSRemarkVlanID1 OBJECT-TYPE
            SYNTAX Integer32 (0 | 1..4094)
            MAX-ACCESS not-accessible
            STATUS current
            DESCRIPTION
                "start Vlan ID.
                -1 can't be set.
                0 is the default value"
            ::= { hwXQoSRemarkEntry 2 }
        
        hwXQoSRemarkVlanID2 OBJECT-TYPE
            SYNTAX Integer32 (0 | 1..4094)
            MAX-ACCESS not-accessible
            STATUS current
            DESCRIPTION
                "end Vlan ID.
                -1 can't be set.
                0 is the default value"
            ::= { hwXQoSRemarkEntry 3 }
        
        hwXQoSIfEnableRemarkAction OBJECT-TYPE
            SYNTAX INTEGER {
             enabled(1),
             unenabled(2)
            }
            MAX-ACCESS read-create
            STATUS current
            DESCRIPTION
                " The enable remark action 
                enabled(1),
                unenabled(2)"
            ::= { hwXQoSRemarkEntry 4 }
        
        hwXQoSRemarkRowStatus OBJECT-TYPE
            SYNTAX RowStatus
            MAX-ACCESS read-create
            STATUS current
            DESCRIPTION
                "RowStatus. Three actions are used: active,
                createAndGo, destroy"
            ::= { hwXQoSRemarkEntry 5 }
            
--   phb enable command begin
        hwXQoSPhbEnableTable OBJECT-TYPE
            SYNTAX SEQUENCE OF HwXQoSPhbEnableEntry
            MAX-ACCESS not-accessible
            STATUS current
            DESCRIPTION
                "PHB enable table."
            ::= { hwXQoSBaObjects 19 }
        
        hwXQoSPhbEnableEntry OBJECT-TYPE
            SYNTAX HwXQoSPhbEnableEntry
            MAX-ACCESS not-accessible
            STATUS current
            DESCRIPTION
                "A table of diff-serve domain phb enable information."
            INDEX { hwXQoSPhbEnableIfIndex,hwXQoSPhbEnableVlanID1,hwXQoSPhbEnableVlanID2 }
            ::= { hwXQoSPhbEnableTable 1 }
        
        HwXQoSPhbEnableEntry ::=
            SEQUENCE { 
                hwXQoSPhbEnableIfIndex
                    Integer32,
                hwXQoSPhbEnableVlanID1
                    Integer32,
                hwXQoSPhbEnableVlanID2
                    Integer32,
                hwXQoSPhbEnableRowStatus
                    RowStatus
             }
        
        hwXQoSPhbEnableIfIndex OBJECT-TYPE
            SYNTAX Integer32
            MAX-ACCESS not-accessible
            STATUS current
            DESCRIPTION
                "Interface Index, equal to ifIndex."
            ::= { hwXQoSPhbEnableEntry 1 }
        
        hwXQoSPhbEnableVlanID1 OBJECT-TYPE
            SYNTAX Integer32 (0 | 1..4094)
            MAX-ACCESS not-accessible
            STATUS current
            DESCRIPTION
                "start Vlan ID.
                -1 can't be set.
                0 is the default value"
            ::= { hwXQoSPhbEnableEntry 2 }
        
        hwXQoSPhbEnableVlanID2 OBJECT-TYPE
            SYNTAX Integer32 (0 | 1..4094)
            MAX-ACCESS not-accessible
            STATUS current
            DESCRIPTION
                "end Vlan ID.
                -1 can't be set.
                0 is the default value"
            ::= { hwXQoSPhbEnableEntry 3 }
        
        hwXQoSPhbEnableRowStatus OBJECT-TYPE
            SYNTAX RowStatus
            MAX-ACCESS read-create
            STATUS current
            DESCRIPTION
                "RowStatus. Three actions are used: active,
                createAndGo, destroy"
            ::= { hwXQoSPhbEnableEntry 4 }
--   phb enable command end
       

-- ******************************************************************
--
--   hwXQoSCommonInboundTable
--
-- ****************************************************************** 


       hwXQoSCommonInboundTable OBJECT-TYPE
          SYNTAX      SEQUENCE OF HwXQoSCommonInboundEntry
          MAX-ACCESS  not-accessible
          STATUS      current
          DESCRIPTION
              " This table is used to configure mapping between the 802.1p priorities or the Differentiated Services
                CodePoint (DSCP) values of upstream packets in the current QinQ domain and service classes. "
          ::= { hwXQoSBaObjects 20 }
          

       hwXQoSCommonInboundEntry OBJECT-TYPE
          SYNTAX HwXQoSCommonInboundEntry
          MAX-ACCESS not-accessible
          STATUS current
          DESCRIPTION
               " This table is used to configure mapping between the 802.1p priorities or the Differentiated Services
                CodePoint (DSCP) values of upstream packets in the current QinQ domain and service classes. " 
          INDEX  { hwXQoSBaIndex, hwXQoSCommonInboundPhbIndex }    
          ::= { hwXQoSCommonInboundTable 1 }           

       HwXQoSCommonInboundEntry ::=
        SEQUENCE {
                hwXQoSCommonInboundPhbIndex                
                    Integer32,
                hwXQoSCommonInboundPhbCos                    
                    INTEGER,
                hwXQoSCommonInboundPhbColor
                    INTEGER,   
                hwXQoSCommonInboundPhbPri
                    Integer32,
                hwXQoSCommonInboundRowStatus          
                    RowStatus
       }

       hwXQoSCommonInboundPhbIndex OBJECT-TYPE
           SYNTAX Integer32
           MAX-ACCESS read-only
           STATUS current
           DESCRIPTION
           " This object indicates a PHB index. "     
           ::= { hwXQoSCommonInboundEntry 1 }

  
       hwXQoSCommonInboundPhbCos OBJECT-TYPE
           SYNTAX INTEGER 
           {
              be(1),
              af1(2),
              af2(3),
              af3(4),
              af4(5),
              ef(6),
              cs6(7),
              cs7(8)
           }

           MAX-ACCESS read-create
           STATUS current
           DESCRIPTION  
           " This object indicates the 802.1p priority or the DSCP value."        
           ::= { hwXQoSCommonInboundEntry 2 }
      

      hwXQoSCommonInboundPhbColor OBJECT-TYPE
           SYNTAX INTEGER 
           {
               green(1),
               yellow(2),
               red(3)
           }
           MAX-ACCESS read-create
           STATUS current
           DESCRIPTION
           " This object indicates the color for marking a type of packets.
             The value can be:
             1: Green
             2: Yellow
             3: Red 
           "    
      
           ::= { hwXQoSCommonInboundEntry 3 }
      
      hwXQoSCommonInboundPhbPri OBJECT-TYPE
           SYNTAX Integer32 (0..7) 
           MAX-ACCESS read-only
           STATUS current
           DESCRIPTION
           " The value of this object identifies the CoS.
             The value ranges from 0 to 7. 
           "
    
           ::= { hwXQoSCommonInboundEntry 4 }   
           

      hwXQoSCommonInboundRowStatus OBJECT-TYPE
           SYNTAX RowStatus 
           MAX-ACCESS read-create
           STATUS current
           DESCRIPTION
           "This object indicates the row status.Currently, three row statuses are supported: Active, CreateAndGo, and Destroy. "
            
           ::= { hwXQoSCommonInboundEntry 50 }   
                                                                              
-- ******************************************************************
--
--   hwXQoSPppInboundTable
--
-- ****************************************************************** 
      hwXQoSPppInboundTable OBJECT-TYPE
          SYNTAX      SEQUENCE OF HwXQoSPppInboundEntry
          MAX-ACCESS  not-accessible
          STATUS      current
          DESCRIPTION
              " This table is used to map the priorities of PPP packets to the internal precedence of a router. "
          ::= { hwXQoSBaObjects 21 }
          

      hwXQoSPppInboundEntry OBJECT-TYPE
          SYNTAX HwXQoSPppInboundEntry
          MAX-ACCESS not-accessible
          STATUS current
          DESCRIPTION
              " This table is used to map the priorities of PPP packets to the internal precedence of a router. " 
          INDEX  { hwXQoSBaIndex }    
          ::= { hwXQoSPppInboundTable 1 }           

      HwXQoSPppInboundEntry ::=
        SEQUENCE {
                hwXQoSPppInboundCos                   
                    INTEGER,
                hwXQoSPppInboundColor  
                    INTEGER,   
                hwXQoSPppInboundRowStatus          
                    RowStatus
        }
  
      hwXQoSPppInboundCos OBJECT-TYPE
           SYNTAX INTEGER 
           {
              be(1),
              af1(2),
              af2(3),
              af3(4),
              af4(5),
              ef(6),
              cs6(7),
              cs7(8)
           }
           MAX-ACCESS read-create
           STATUS current
           DESCRIPTION
           " This object indicates the CoS of a router.
             The value can be:
            1: BE  
            2: AF1
            3. AF2
            4: AF3
            5: AF4
            6: EF
            7: CS6
            8: CS7 
           " 
 
           ::= { hwXQoSPppInboundEntry 1 }
      

      hwXQoSPppInboundColor OBJECT-TYPE
           SYNTAX INTEGER
           {
               green(1),
               yellow(2),
               red(3)
           } 
           MAX-ACCESS read-create
           STATUS current
           DESCRIPTION
           " This object indicates the color for marking PPP packets.
             The value can be:
             1: Green
             2: Yellow
             3; Red
           "    
      
           ::= { hwXQoSPppInboundEntry 2 }
      

      hwXQoSPppInboundRowStatus OBJECT-TYPE
           SYNTAX RowStatus 
           MAX-ACCESS read-create
           STATUS current
           DESCRIPTION
           "This object indicates the row status.Currently, three row statuses are supported: Active, CreateAndGo, and Destroy."
            
           ::= { hwXQoSPppInboundEntry 50 }  
         
            

-- ******************************************************************
--
--   hwXQoSServiceclassTable
--
-- ******************************************************************  

      hwXQoSServiceclassTable OBJECT-TYPE
          SYNTAX      SEQUENCE OF HwXQoSServiceclassEntry
          MAX-ACCESS  not-accessible
          STATUS      current
          DESCRIPTION
              " This table is used to configure upstream traffic to enter specified queues on the interface. "
          ::= { hwXQoSBaObjects 22 }
          

      hwXQoSServiceclassEntry OBJECT-TYPE
          SYNTAX HwXQoSServiceclassEntry
          MAX-ACCESS not-accessible
          STATUS current
          DESCRIPTION
              " This table is used to configure upstream traffic to enter specified queues on the interface. " 
          INDEX  { hwXQoSServiceclassPort }    
          ::= { hwXQoSServiceclassTable 1 }           

       HwXQoSServiceclassEntry ::=
        SEQUENCE {
                hwXQoSServiceclassPort                
                    InterfaceIndex, 
                hwXQoSServiceclass
                     INTEGER,    
                hwXQoSServiceclassRowStatus          
                    RowStatus
         }

      hwXQoSServiceclassPort OBJECT-TYPE
          SYNTAX InterfaceIndex
          MAX-ACCESS read-only
          STATUS current
          DESCRIPTION
          " This object indicates the interface index."     
          ::= { hwXQoSServiceclassEntry 1 }
      

      hwXQoSServiceclass OBJECT-TYPE
          SYNTAX INTEGER
          {
              be(1),
              af1(2),
              af2(3),
              af3(4),
              af4(5),
              ef(6),
              cs6(7),
              cs7(8)
          }
          MAX-ACCESS read-create
          STATUS current
          DESCRIPTION
          " This object indicates the CoS of the queue that upstream traffic on an interface enters. "     
          ::= { hwXQoSServiceclassEntry 2 }


      hwXQoSServiceclassRowStatus OBJECT-TYPE
          SYNTAX RowStatus 
          MAX-ACCESS read-create
          STATUS current
          DESCRIPTION
          "This object indicates the row status.Currently, three row statuses are supported: Active, CreateAndGo, and Destroy. "  
          ::= { hwXQoSServiceclassEntry 50 }  



-- ******************************************************************
--
--   hwXQoSPhbTable
--
-- ******************************************************************  

      hwXQoSPhbTable       OBJECT-TYPE
          SYNTAX      SEQUENCE OF HwXQoSPhbEntry
          MAX-ACCESS  not-accessible
          STATUS      current
          DESCRIPTION
              " This table is used to prohibit the function of checking the PHB table on the outgoing interface. "
          ::= { hwXQoSBaObjects 23 }
          

      hwXQoSPhbEntry OBJECT-TYPE
          SYNTAX HwXQoSPhbEntry
          MAX-ACCESS not-accessible
          STATUS current
          DESCRIPTION
              " This table is used to prohibit the function of checking the PHB table on the outgoing interface. " 
          INDEX  { hwXQoSPhbPort }    
          ::= { hwXQoSPhbTable 1 }           

      HwXQoSPhbEntry ::=
        SEQUENCE {
                hwXQoSPhbPort                
                    InterfaceIndex, 
                hwXQoSPhbEnable
                    INTEGER,  
                hwXQoSPhbRowStatus          
                    RowStatus
        }

      hwXQoSPhbPort OBJECT-TYPE
          SYNTAX InterfaceIndex
          MAX-ACCESS read-only
          STATUS current
          DESCRIPTION
          " This object indicates the interface index. "     
          ::= { hwXQoSPhbEntry 1 }

      hwXQoSPhbEnable OBJECT-TYPE
          SYNTAX INTEGER
          {
              enable(1),
              disable(2)
          }
          MAX-ACCESS read-create
          STATUS current
          DESCRIPTION
          " This object indicates the CoS of the queue that upstream traffic on an interface enters. "  
          DEFVAL {1}  
          ::= { hwXQoSPhbEntry 2 }
      

      hwXQoSPhbRowStatus OBJECT-TYPE
          SYNTAX RowStatus 
          MAX-ACCESS read-create
          STATUS current
          DESCRIPTION
          "This object indicates the row status.Currently, three row statuses are supported: Active, CreateAndGo, and Destroy. "
            
          ::= { hwXQoSPhbEntry 50 }      

-- ******************************************************************
--
--   hwXQoSFieldDeiTable
--
-- ******************************************************************

      hwXQoSFieldDeiTable OBJECT-TYPE
          SYNTAX      SEQUENCE OF HwXQoSFieldDeiEntry
          MAX-ACCESS  not-accessible
          STATUS      current
          DESCRIPTION
              " This table is sued to enable the drop eligible indicator (DEI) capability of the packets
                on an interface and in a specified VLAN range. "
          ::= { hwXQoSBaObjects 24 }
          

      hwXQoSFieldDeiEntry OBJECT-TYPE
          SYNTAX HwXQoSFieldDeiEntry
          MAX-ACCESS not-accessible
          STATUS current
          DESCRIPTION
              " This table is sued to enable the drop eligible indicator (DEI) capability of the packets 
                on an interface and in a specified VLAN range. " 
          INDEX  { hwXQoSFieldDeiInterface,hwXQoSFieldDeiVlanId }    
          ::= { hwXQoSFieldDeiTable 1 }           

      HwXQoSFieldDeiEntry ::=
        SEQUENCE {
                hwXQoSFieldDeiInterface                
                    InterfaceIndex,
                hwXQoSFieldDeiVlanId  
                    Integer32,           
                hwXQoSFieldDeiEnabled 
                    Integer32,
                hwXQoSFieldDeiRowStatus          
                    RowStatus
        }

      hwXQoSFieldDeiInterface OBJECT-TYPE
           SYNTAX InterfaceIndex
           MAX-ACCESS read-only
           STATUS current
           DESCRIPTION
           " This object indicates the interface index. "     
           ::= { hwXQoSFieldDeiEntry 1 }

  
      hwXQoSFieldDeiVlanId OBJECT-TYPE
           SYNTAX Integer32 (1..4094)
           MAX-ACCESS read-only
           STATUS current
           DESCRIPTION
           " The value of this object identifies the VLAN ID.
             The value ranges from 1 to 4094. 
           "
           ::= { hwXQoSFieldDeiEntry 2 }           
            

      hwXQoSFieldDeiEnabled OBJECT-TYPE
           SYNTAX Integer32 (0..2)
           MAX-ACCESS read-create
           STATUS current
           DESCRIPTION
           " The value of this object identifies whether to enable the DEI capability of the packets on a VLAN. "    
           ::= { hwXQoSFieldDeiEntry 3 }


      hwXQoSFieldDeiRowStatus OBJECT-TYPE
           SYNTAX RowStatus 
           MAX-ACCESS read-create
           STATUS current
           DESCRIPTION
           "This object indicates the row status.Currently, three row statuses are supported: Active, CreateAndGo, and Destroy."
            
           ::= { hwXQoSFieldDeiEntry 50 }           

-- ******************************************************************
--
--   hwXQoSPicForwardingTable
--
-- ******************************************************************

      hwXQoSPicForwardingTable OBJECT-TYPE
          SYNTAX      SEQUENCE OF HwXQoSPicForwardingEntry
          MAX-ACCESS  not-accessible
          STATUS      current
          DESCRIPTION
              " hwXQoSPicForwardingTable "
          ::= { hwXQoSBaObjects 25 }
          

      hwXQoSPicForwardingEntry OBJECT-TYPE
          SYNTAX HwXQoSPicForwardingEntry
          MAX-ACCESS not-accessible
          STATUS current
          DESCRIPTION
              " hwXQoSPicForwardingEntry " 
          INDEX  { hwXQoSPicForwardingInterface }    
          ::= { hwXQoSPicForwardingTable 1 }           

      HwXQoSPicForwardingEntry ::=
        SEQUENCE {
                hwXQoSPicForwardingInterface                
                    InterfaceIndex,
                hwXQoSPicForwarding8021pValue  
                    Integer32,   
                hwXQoSPicForwardingPriority 
                    INTEGER,
                hwXQoSPicForwardingRowStatus          
                    RowStatus
        }

      hwXQoSPicForwardingInterface OBJECT-TYPE
          SYNTAX InterfaceIndex
          MAX-ACCESS read-only
          STATUS current
          DESCRIPTION
          " hwXQoSPicForwardingInterface "     
          ::= { hwXQoSPicForwardingEntry 1 }

  
      hwXQoSPicForwarding8021pValue OBJECT-TYPE
          SYNTAX Integer32 (0..8)
          MAX-ACCESS read-create
          STATUS current
          DESCRIPTION
          " hwXQoSPicForwarding8021pValue "
          ::= { hwXQoSPicForwardingEntry 2 } 
             

      hwXQoSPicForwardingPriority OBJECT-TYPE
          SYNTAX INTEGER
          {
              high(1)
          }
          MAX-ACCESS read-create
          STATUS current
          DESCRIPTION
          " hwXQoSPicForwardingPriority "    
          ::= { hwXQoSPicForwardingEntry 3 }


      hwXQoSPicForwardingRowStatus OBJECT-TYPE
          SYNTAX RowStatus 
          MAX-ACCESS read-create
          STATUS current
          DESCRIPTION
          "
            Row status. The value ranges from 1 to 6 but usually 4 and 6 are used.
            createAndGo[4] - create a row.        
            destroy[6] -delete a row.       
          "
            
      ::= { hwXQoSPicForwardingEntry 4 }              



-- ******************************************************************
--
--   hwXQoSCarTable
--
-- ******************************************************************

      hwXQoSCarTable OBJECT-TYPE
          SYNTAX      SEQUENCE OF HwXQoSCarEntry
          MAX-ACCESS  not-accessible
          STATUS      current
          DESCRIPTION
              " This table is used to configure traffic policing on a Layer 3 main interface or a Layer 2 interface. "
          ::= { hwXQoSBaObjects 26 }
          

      hwXQoSCarEntry OBJECT-TYPE
          SYNTAX HwXQoSCarEntry
          MAX-ACCESS not-accessible
          STATUS current
          DESCRIPTION
              " This table is used to configure traffic policing on a Layer 3 main interface or a Layer 2 interface. " 
          INDEX  { hwXQoSCarInterfaceIndex,hwXQoSCarDirection,hwXQoSCarVlanID }    
          ::= { hwXQoSCarTable 1 }           

      HwXQoSCarEntry ::=
        SEQUENCE {
                hwXQoSCarInterfaceIndex                
                    InterfaceIndex,                     
                hwXQoSCarDirection
                    INTEGER,
                hwXQoSCarVlanID
                    Integer32,
                hwXQoSCarCirValue  
                    Integer32,   
                hwXQoSCarPirValue 
                    Integer32,
                hwXQoSCarCbsValue
                    Integer32,
                hwXQoSCarPbsValue
                    Integer32,
                hwXQoSCarGreenAction
                    INTEGER,
                hwXQoSCarGreenServiceClass
                    INTEGER,
                hwXQoSCarGreenColor
                    INTEGER,
                hwXQoSCarYellowAction
                    INTEGER,
                hwXQoSCarYellowServiceClass
                    INTEGER,  
                hwXQoSCarYellowColor
                    INTEGER,
                hwXQoSCarRedAction
                    INTEGER,
                hwXQoSCarRedServiceClass
                    INTEGER,
                hwXQoSCarRedColor
                    INTEGER,    
                hwXQoSCarRowStatus          
                    RowStatus,
                hwXQoSCarCirValueEx 
                    Unsigned32,   
                hwXQoSCarPirValueEx 
                    Unsigned32,
                hwXQoSCarCbsValueEx
                    Unsigned32,
                hwXQoSCarPbsValueEx
                    Unsigned32
        }

      hwXQoSCarInterfaceIndex OBJECT-TYPE
          SYNTAX InterfaceIndex
          MAX-ACCESS read-only
          STATUS current
          DESCRIPTION
          " This object indicates the interface index."     
          ::= { hwXQoSCarEntry 1 }

      hwXQoSCarDirection OBJECT-TYPE
          SYNTAX INTEGER
          {
              inbound(1),
              outbound(2)
          }
          MAX-ACCESS read-only
          STATUS current
          DESCRIPTION
          " This object indicates the direction where the CAR on an interface is applied.
            The value can be:
            1: inbound
            2: outbound
          " 
          ::= { hwXQoSCarEntry 2 }
   
      hwXQoSCarVlanID OBJECT-TYPE
          SYNTAX Integer32 (1..4094)
          MAX-ACCESS read-only
          STATUS current
          DESCRIPTION
          " The value of this object identifies the VLAN ID.
            The value ranges from 1 to 4094. "
          ::= { hwXQoSCarEntry 3 } 
          
      hwXQoSCarCirValue OBJECT-TYPE
          SYNTAX Integer32 (0..100000000)
          MAX-ACCESS read-create
          STATUS current
          DESCRIPTION
          " The value of this object identifies the CIR on an interface."
          ::= { hwXQoSCarEntry 4 } 

      hwXQoSCarPirValue OBJECT-TYPE
          SYNTAX Integer32  (-1 | 0..100000000)
          MAX-ACCESS read-create
          STATUS current
          DESCRIPTION
          " The value of this object identifies the PIR on an interface."
          ::= { hwXQoSCarEntry 5 } 

      hwXQoSCarCbsValue OBJECT-TYPE
          SYNTAX Integer32 (0..100000000)
          MAX-ACCESS read-create
          STATUS current
          DESCRIPTION
          " The value of this object identifies the CBS on an interface."
          ::= { hwXQoSCarEntry 6 }

      hwXQoSCarPbsValue OBJECT-TYPE
          SYNTAX Integer32 (0..100000000)
          MAX-ACCESS read-create
          STATUS current
          DESCRIPTION
          " The value of this object identifies the PBS on an interface."
          ::= { hwXQoSCarEntry 7 }

      hwXQoSCarGreenAction OBJECT-TYPE
          SYNTAX INTEGER
          {
              pass(1),
              discard(2),
              null(3)
          }
          MAX-ACCESS read-create
          STATUS current
          DESCRIPTION
          " This object indicates the action taken on the packets marked in green.
          " 
          ::= { hwXQoSCarEntry 8 }

      hwXQoSCarGreenServiceClass OBJECT-TYPE
          SYNTAX INTEGER
          {
              be(1),
              af1(2),
              af2(3),
              af3(4),
              af4(5),
              ef(6),
              cs6(7),
              cs7(8),
              null(9)
          }
          MAX-ACCESS read-create
          STATUS current
          DESCRIPTION
          " This object indicates the service class of the packets marked in green to be re-marked.
            The value can be:
            1: BE  
            2: AF1
            3. AF2
            4: AF3
            5: AF4
            6: EF
            7: CS6
            8: CS7
            9: null " 
          ::= { hwXQoSCarEntry 9 }

      hwXQoSCarGreenColor OBJECT-TYPE
          SYNTAX INTEGER
          {
              green(1),
              yellow(2),
              red(3),
              null(4)
          }
          MAX-ACCESS read-create
          STATUS current
          DESCRIPTION
          " This object indicates the color in which the packets marked in green are to be re-marked.
            The value can be:
            1: green
            2: yellow
            3: red
            4: null " 
          ::= { hwXQoSCarEntry 10 }

      hwXQoSCarYellowAction OBJECT-TYPE
          SYNTAX INTEGER
          {
              pass(1),
              discard(2),
              null(3)
          }
          MAX-ACCESS read-create
          STATUS current
          DESCRIPTION
          " This object indicates the action taken on the packets marked in yellow." 
          ::= { hwXQoSCarEntry 11 }

      hwXQoSCarYellowServiceClass OBJECT-TYPE
          SYNTAX INTEGER
          {
              be(1),
              af1(2),
              af2(3),
              af3(4),
              af4(5),
              ef(6),
              cs6(7),
              cs7(8),
              null(9)
          }
          MAX-ACCESS read-create
          STATUS current
          DESCRIPTION
          " This object indicates the service class of the packets marked in yellow to be re-marked.
            The value can be:
            1: BE  
            2: AF1
            3. AF2
            4: AF3
            5: AF4
            6: EF
            7: CS6
            8: CS7
            9: null " 

          ::= { hwXQoSCarEntry 12 }

      hwXQoSCarYellowColor OBJECT-TYPE
          SYNTAX INTEGER
          {
              green(1),
              yellow(2),
              red(3),
              null(4)
          }
          MAX-ACCESS read-create
          STATUS current
          DESCRIPTION
          " This object indicates the color in which the packets marked in yellow are to be re-marked.
            The value can be:
            1: green
            2: yellow
            3: red
            4: null " 
          ::= { hwXQoSCarEntry 13 }

      hwXQoSCarRedAction OBJECT-TYPE
          SYNTAX INTEGER
          {
              pass(1),
              discard(2),
              null(3)
          }
          MAX-ACCESS read-create
          STATUS current
          DESCRIPTION
          " This object indicates the action taken on the packets marked in red.
            The value can be:
            1: pass
            2: discard
            3: null
            The default value is discard. " 
          DEFVAL {2} 
          ::= { hwXQoSCarEntry 14 }

      hwXQoSCarRedServiceClass OBJECT-TYPE
          SYNTAX INTEGER
          {
              be(1),
              af1(2),
              af2(3),
              af3(4),
              af4(5),
              ef(6),
              cs6(7),
              cs7(8),
              null(9)
          }
          MAX-ACCESS read-create
          STATUS current
          DESCRIPTION
          " This object indicates the service class of the packets marked in red to be re-marked.
            The value can be:
            1: BE  
            2: AF1
            3. AF2
            4: AF3
            5: AF4
            6: EF
            7: CS6
            8: CS7
            9: null " 

          ::= { hwXQoSCarEntry 15 }

      hwXQoSCarRedColor OBJECT-TYPE
          SYNTAX INTEGER
          {
              green(1),
              yellow(2),
              red(3),
              null(4)
          }
          MAX-ACCESS read-create
          STATUS current
          DESCRIPTION
          " This object indicates the color in which the packets marked in yellow are to be re-marked.
            The value can be:
            1: green
            2: yellow
            3: red
            4: null " 
          ::= { hwXQoSCarEntry 16 }         
                
      hwXQoSCarRowStatus OBJECT-TYPE
          SYNTAX RowStatus 
          MAX-ACCESS read-create
          STATUS current
          DESCRIPTION
          "This object indicates the row status.Currently, three row statuses are supported: Active, CreateAndGo, and Destroy."
            
      ::= { hwXQoSCarEntry 50 }  

      hwXQoSCarCirValueEx OBJECT-TYPE
          SYNTAX Unsigned32
          MAX-ACCESS read-create
          STATUS current
          DESCRIPTION
          " The value of this object identifies the CIR on an interface."
          ::= { hwXQoSCarEntry 51 } 

      hwXQoSCarPirValueEx OBJECT-TYPE
          SYNTAX Unsigned32
          MAX-ACCESS read-create
          STATUS current
          DESCRIPTION
          " The value of this object identifies the PIR on an interface."
          ::= { hwXQoSCarEntry 52 } 

      hwXQoSCarCbsValueEx OBJECT-TYPE
          SYNTAX Unsigned32
          MAX-ACCESS read-create
          STATUS current
          DESCRIPTION
          " The value of this object identifies the CBS on an interface."
          ::= { hwXQoSCarEntry 53 }

      hwXQoSCarPbsValueEx OBJECT-TYPE
          SYNTAX Unsigned32
          MAX-ACCESS read-create
          STATUS current
          DESCRIPTION
          " The value of this object identifies the PBS on an interface."
          ::= { hwXQoSCarEntry 54 }


-- ******************************************************************
--
--   hwXQoSPortShapingTable
--
-- ******************************************************************

      hwXQoSPortShapingTable OBJECT-TYPE
          SYNTAX      SEQUENCE OF HwXQoSPortShapingEntry
          MAX-ACCESS  not-accessible
          STATUS      current
          DESCRIPTION
              " This table is used to limit the rate at which packets are sent on an interface. "
          ::= { hwXQoSBaObjects 27 }
          

      hwXQoSPortShapingEntry OBJECT-TYPE
          SYNTAX HwXQoSPortShapingEntry
          MAX-ACCESS not-accessible
          STATUS current
          DESCRIPTION
              " This table is used to limit the rate at which packets are sent on an interface. " 
          INDEX  { hwXQoSPortShapingInterface }    
          ::= { hwXQoSPortShapingTable 1 }           

      HwXQoSPortShapingEntry ::=
        SEQUENCE {
                hwXQoSPortShapingInterface                
                    InterfaceIndex,
                hwXQoSPortShapingValue  
                    OCTET STRING,   
                hwXQoSPortShapingPbsValue  
                    Integer32,   
                hwXQoSPortShapingRowStatus          
                    RowStatus
        }

      hwXQoSPortShapingInterface OBJECT-TYPE
          SYNTAX InterfaceIndex
          MAX-ACCESS read-only
          STATUS current
          DESCRIPTION
          " This object indicates the interface index."     
          ::= { hwXQoSPortShapingEntry 1 }

  
      hwXQoSPortShapingValue OBJECT-TYPE
          SYNTAX OCTET STRING (SIZE (1..10))
          MAX-ACCESS read-create
          STATUS current
          DESCRIPTION
          " The value of this object identifies the shaping rate.
            The maximum value equals the interface bandwidth. "
          ::= { hwXQoSPortShapingEntry 2 } 

      hwXQoSPortShapingPbsValue OBJECT-TYPE
          SYNTAX Integer32 (1..262144)
          MAX-ACCESS read-create
          STATUS current
          DESCRIPTION
          " This object indicates the PBS.
            The value is an integer that ranges from 1 to 262144, in bytes.
            the default pbs-value is 131072. 
          "
          ::= { hwXQoSPortShapingEntry 3 }

      hwXQoSPortShapingRowStatus OBJECT-TYPE
          SYNTAX RowStatus 
          MAX-ACCESS read-create
          STATUS current
          DESCRIPTION
          "This object indicates the row status."
            
      ::= { hwXQoSPortShapingEntry 50 }   

-- ******************************************************************
--
--   hwXQoSQueueTable
--
-- ******************************************************************

      hwXQoSQueueTable OBJECT-TYPE
          SYNTAX      SEQUENCE OF HwXQoSQueueEntry
          MAX-ACCESS  not-accessible
          STATUS      current
          DESCRIPTION
              " hwXQoSQueueTable "
          ::= { hwXQoSBaObjects 28 }
          

      hwXQoSQueueEntry OBJECT-TYPE
          SYNTAX HwXQoSQueueEntry
          MAX-ACCESS not-accessible
          STATUS current
          DESCRIPTION
              " hwXQoSQueueEntry " 
          INDEX  { hwXQoSQueueInterfaceIndex }    
          ::= { hwXQoSQueueTable 1 }           

      HwXQoSQueueEntry ::=
        SEQUENCE {
                hwXQoSQueueInterfaceIndex                
                    InterfaceIndex,
                hwXQoSQueueServiceClass
                    INTEGER,
                hwXQoSQueueCirValue  
                    Integer32,
                hwXQoSQueueCirPercentage
                    Integer32,
                hwXQoSQueueDirection
                    INTEGER,   
                hwXQoSQueueRowStatus          
                    RowStatus
        }

      hwXQoSQueueInterfaceIndex OBJECT-TYPE
          SYNTAX InterfaceIndex
          MAX-ACCESS read-only
          STATUS current
          DESCRIPTION
          " hwXQoSQueueInterfaceIndex "     
          ::= { hwXQoSQueueEntry 1 }

      hwXQoSQueueServiceClass OBJECT-TYPE
          SYNTAX INTEGER
          {
              be(1),
              af1(2),
              af2(3),
              af3(4),
              af4(5),
              ef(6),
              cs6(7),
              cs7(8)
          }
          MAX-ACCESS read-create
          STATUS current
          DESCRIPTION
          " hwXQoSQueueServiceClass " 
          ::= { hwXQoSQueueEntry 2 }

  
      hwXQoSQueueCirValue OBJECT-TYPE
          SYNTAX Integer32 (0..10000)
          MAX-ACCESS read-create
          STATUS current
          DESCRIPTION
          " hwXQoSQueueCirValue "
          ::= { hwXQoSQueueEntry 3 } 
          
  
      hwXQoSQueueCirPercentage OBJECT-TYPE
          SYNTAX Integer32 (0..100)
          MAX-ACCESS read-create
          STATUS current
          DESCRIPTION
          " hwXQoSQueueCirPercentage "
          ::= { hwXQoSQueueEntry 4 } 

      hwXQoSQueueDirection OBJECT-TYPE
          SYNTAX INTEGER
          {
              inbound(1),
              outbound(2)
          }
          MAX-ACCESS read-create
          STATUS current
          DESCRIPTION
          " hwXQoSQueueDirection " 
          ::= { hwXQoSQueueEntry 5 }


      hwXQoSQueueRowStatus OBJECT-TYPE
          SYNTAX RowStatus 
          MAX-ACCESS read-create
          STATUS current
          DESCRIPTION
          "
            Row status. The value ranges from 1 to 6 but usually 4 and 6 are used.
            createAndGo[4] - create a row.        
            destroy[6] -delete a row.       
          "
            
      ::= { hwXQoSQueueEntry 6 }  
 
-- ******************************************************************
--
--   hwXQoSCarStatisticsTable
--
-- ******************************************************************

      hwXQoSCarStatisticsTable OBJECT-TYPE
          SYNTAX      SEQUENCE OF HwXQoSCarStatisticsEntry
          MAX-ACCESS  not-accessible
          STATUS      current
          DESCRIPTION
              " This table is used to query the CAR statistics on an interface. "
          ::= { hwXQoSBaObjects 29 }
          

      hwXQoSCarStatisticsEntry OBJECT-TYPE
          SYNTAX HwXQoSCarStatisticsEntry
          MAX-ACCESS not-accessible
          STATUS current
          DESCRIPTION
              " This table is used to query the CAR statistics on an interface. " 
          INDEX  { hwXQoSCarStatisticsInterfaceIndex,hwXQoSCarStatisticsDirection,hwXQoSCarStatisticsVlanid,hwXQoSCarStatisticsSlotNumber}    
          ::= { hwXQoSCarStatisticsTable 1 }           

      HwXQoSCarStatisticsEntry ::=
        SEQUENCE {
                hwXQoSCarStatisticsInterfaceIndex                
                    InterfaceIndex, 
                hwXQoSCarStatisticsDirection  
                    INTEGER,
                hwXQoSCarStatisticsVlanid
                    Integer32,
                hwXQoSCarStatisticsSlotNumber
                    Integer32,
                hwXQoSCarStatisticsReset 
                    INTEGER,             
                hwXQoSCarStatisticsPassPackets 
                    Counter64,   
                hwXQoSCarStatisticsPassBytes 
                    Counter64, 
                hwXQoSCarStatisticsDropPackets 
                    Counter64, 
                hwXQoSCarStatisticsDropBytes 
                    Counter64,
                hwXQoSCarStatisticsPassPacketsRate
                    Counter64,
                hwXQoSCarStatisticsPassBytesRate 
                    Counter64,
                hwXQoSCarStatisticsDropPacketsRate 
                    Counter64,
                hwXQoSCarStatisticsDropBytesRate 
                    Counter64
        }

      hwXQoSCarStatisticsInterfaceIndex OBJECT-TYPE
          SYNTAX InterfaceIndex
          MAX-ACCESS read-only
          STATUS current
          DESCRIPTION
          " This object indicates the interface index."     
          ::= { hwXQoSCarStatisticsEntry 1 }

      hwXQoSCarStatisticsDirection OBJECT-TYPE
          SYNTAX INTEGER
          {
              inbound(1),
              outbound(2)
          }
          MAX-ACCESS read-only
          STATUS current
          DESCRIPTION
          " This object indicates the direction where the CAR statistics are queried.
            The value can be:
            1: inbound
            2: outbound 
          " 
          ::= { hwXQoSCarStatisticsEntry 2 }

      hwXQoSCarStatisticsVlanid OBJECT-TYPE
          SYNTAX Integer32 (0..4094)
          MAX-ACCESS read-only
          STATUS current
          DESCRIPTION
          " The value of this object identifies the VLAN ID of an interface where the CAR statistics are queried.
            The value ranges from 1 to 4094. "
          ::= { hwXQoSCarStatisticsEntry 3 } 

      hwXQoSCarStatisticsSlotNumber OBJECT-TYPE
          SYNTAX Integer32 (0..128)
          MAX-ACCESS read-only
          STATUS current
          DESCRIPTION
          " The value of this object identifies the number of the slot where the CAR statistics are queried.
            The value ranges from 0 to 128.
            0 indicates that statistics of all the slots are collected. "
          ::= { hwXQoSCarStatisticsEntry 4 } 

      hwXQoSCarStatisticsReset OBJECT-TYPE
          SYNTAX INTEGER
          {
              reset(1)
          }
          MAX-ACCESS read-create
          STATUS current
          DESCRIPTION
          " This object indicates the resetting of statistics. " 
          ::= { hwXQoSCarStatisticsEntry 5 }

      hwXQoSCarStatisticsPassPackets OBJECT-TYPE
            SYNTAX  Counter64
            MAX-ACCESS read-only
            STATUS current
            DESCRIPTION
            " This object indicates the number of passed packets. "    
            ::= { hwXQoSCarStatisticsEntry 6 }             

      hwXQoSCarStatisticsPassBytes OBJECT-TYPE
            SYNTAX  Counter64
            MAX-ACCESS read-only
            STATUS current
            DESCRIPTION
            " This object indicates the number of passed bytes. "    
            ::= { hwXQoSCarStatisticsEntry 7 }                

      hwXQoSCarStatisticsDropPackets OBJECT-TYPE
            SYNTAX  Counter64
            MAX-ACCESS read-only
            STATUS current
            DESCRIPTION
            " This object indicates the number of discarded packets. "    
            ::= { hwXQoSCarStatisticsEntry 8 }                

      hwXQoSCarStatisticsDropBytes OBJECT-TYPE
            SYNTAX  Counter64
            MAX-ACCESS read-only
            STATUS current
            DESCRIPTION
            " This object indicates the number of discarded bytes. "    
            ::= { hwXQoSCarStatisticsEntry 9 }  

      hwXQoSCarStatisticsPassPacketsRate OBJECT-TYPE
            SYNTAX  Counter64
            MAX-ACCESS read-only
            STATUS current
            DESCRIPTION
            " This object indicates the packet pass rate. "    
            ::= { hwXQoSCarStatisticsEntry 10 }  

      hwXQoSCarStatisticsPassBytesRate  OBJECT-TYPE
            SYNTAX  Counter64
            MAX-ACCESS read-only
            STATUS current
            DESCRIPTION
            " This object indicates the byte pass rate.  "    
            ::= { hwXQoSCarStatisticsEntry 11 }

      hwXQoSCarStatisticsDropPacketsRate OBJECT-TYPE
            SYNTAX  Counter64
            MAX-ACCESS read-only
            STATUS current
            DESCRIPTION
            " This object indicates the packet drop rate. "    
            ::= { hwXQoSCarStatisticsEntry 12 }

      hwXQoSCarStatisticsDropBytesRate  OBJECT-TYPE
            SYNTAX  Counter64
            MAX-ACCESS read-only
            STATUS current
            DESCRIPTION
            " This object indicates the byte drop rate.  "    
            ::= { hwXQoSCarStatisticsEntry 13 }
 

-- ******************************************************************
--
--   hwXQoSCpRateLimitTable
--
-- ******************************************************************

      hwXQoSCpRateLimitTable OBJECT-TYPE
          SYNTAX      SEQUENCE OF HwXQoSCpRateLimitEntry
          MAX-ACCESS  not-accessible
          STATUS      current
          DESCRIPTION
              " This table is used to set the limit on the rate at which IGMP packets are transmitted. "
          ::= { hwXQoSBaObjects 30 }
          

      hwXQoSCpRateLimitEntry OBJECT-TYPE
          SYNTAX HwXQoSCpRateLimitEntry
          MAX-ACCESS not-accessible
          STATUS current
          DESCRIPTION
              " This table is used to set the limit on the rate at which IGMP packets are transmitted. " 
          INDEX  { hwXQoSCpRateLimitIfIndex,hwXQoSCpRateLimitPeVidValue,hwXQoSCpRateLimitCeVidBegin}    
          ::= { hwXQoSCpRateLimitTable 1 }           

      HwXQoSCpRateLimitEntry ::=
        SEQUENCE {
                hwXQoSCpRateLimitIfIndex                
                    InterfaceIndex, 
                hwXQoSCpRateLimitPeVidValue
                    Integer32,
                hwXQoSCpRateLimitCeVidBegin
                    Integer32,
                hwXQoSCpRateLimitCeVidEnd
                    Integer32,
                hwXQoSCpRateLimitType  
                    INTEGER,
                hwXQoSCpRateLimitIgmpCir
                    Integer32,
                hwXQoSCpRateLimitIgmpCbs
                    Integer32,
                hwXQoSCpRateLimitRowStatus           
                    RowStatus
        }

      hwXQoSCpRateLimitIfIndex OBJECT-TYPE
          SYNTAX InterfaceIndex
          MAX-ACCESS read-only
          STATUS current
          DESCRIPTION
          " This object indicates the index of an interface. "     
          ::= { hwXQoSCpRateLimitEntry 1 }

      hwXQoSCpRateLimitPeVidValue OBJECT-TYPE
          SYNTAX Integer32 (0..4094)
          MAX-ACCESS read-only
          STATUS current
          DESCRIPTION
          " This object indicates an outer VLAN tag.
            The value ranges from 1 to 4094. "
          ::= { hwXQoSCpRateLimitEntry 2 } 

      hwXQoSCpRateLimitCeVidBegin OBJECT-TYPE
          SYNTAX Integer32 (0..4094)
          MAX-ACCESS read-only
          STATUS current
          DESCRIPTION
          " This object indicates the start inner VLAN tag.
            The value ranges from 1 to 4094. "
          ::= { hwXQoSCpRateLimitEntry 3 }

      hwXQoSCpRateLimitCeVidEnd OBJECT-TYPE
          SYNTAX Integer32 (0..4094)
          MAX-ACCESS read-create
          STATUS current
          DESCRIPTION
          " This object indicates the end inner VLAN tag.
            The value ranges from 1 to 4094. "
          ::= { hwXQoSCpRateLimitEntry 4 }

      hwXQoSCpRateLimitType OBJECT-TYPE
          SYNTAX INTEGER
          {
              igmp(1)
          }
          MAX-ACCESS read-create
          STATUS current
          DESCRIPTION
          " The value of this object identifies the type of packets.
             The value can be:
             1: IGMP
          " 
          ::= { hwXQoSCpRateLimitEntry 5 }
  
      hwXQoSCpRateLimitIgmpCir OBJECT-TYPE
          SYNTAX Integer32 (0 | 32..1000000)
          MAX-ACCESS read-create
          STATUS current
          DESCRIPTION
          " This object indicates the packet sending rate.
            The value ranges from 32 to 10000000. "
          ::= { hwXQoSCpRateLimitEntry 6 } 

      hwXQoSCpRateLimitIgmpCbs OBJECT-TYPE
          SYNTAX Integer32 (100..33554432)
          MAX-ACCESS read-create
          STATUS current
          DESCRIPTION
          " This object indicates the CBS of the sent packets.
            The value ranges from 100 to 33554432. "
          ::= { hwXQoSCpRateLimitEntry 7 }              

      hwXQoSCpRateLimitRowStatus  OBJECT-TYPE
          SYNTAX RowStatus 
          MAX-ACCESS read-create
          STATUS current
          DESCRIPTION
          "
            Row status. The value ranges from 1 to 6 but usually 4 and 6 are used.
            createAndGo[4] - create a row.        
            destroy[6] -delete a row.       
          "
      ::= { hwXQoSCpRateLimitEntry 50 }   
 
-- ******************************************************************
--
--   hwXQoSPortQueueStatisticsTable
--
-- ******************************************************************

      hwXQoSPortQueueStatisticsTable OBJECT-TYPE
          SYNTAX      SEQUENCE OF HwXQoSPortQueueStatisticsEntry
          MAX-ACCESS  not-accessible
          STATUS      current
          DESCRIPTION
              " This table is used to query the statistics of class queues. "
          ::= { hwXQoSBaObjects 31 }
          

      hwXQoSPortQueueStatisticsEntry OBJECT-TYPE
          SYNTAX HwXQoSPortQueueStatisticsEntry
          MAX-ACCESS not-accessible
          STATUS current
          DESCRIPTION
              " This table is used to query the statistics of class queues. " 
          INDEX  { hwXQoSPortQueueStatisticsInterfaceIndex,
                   hwXQoSPortQueueStatisticsDirection,
                   hwXQoSPortQueueStatisticsQueueIndex }    
          ::= { hwXQoSPortQueueStatisticsTable 1 }           

      HwXQoSPortQueueStatisticsEntry ::=
        SEQUENCE {
                hwXQoSPortQueueStatisticsInterfaceIndex                 
                    InterfaceIndex,                                          
                hwXQoSPortQueueStatisticsDirection  
                    INTEGER,                                                        
                hwXQoSPortQueueStatisticsQueueIndex  
                    INTEGER,                                           
                hwXQoSPortQueueStatisticsReset  
                    INTEGER,                         
                hwXQoSPortQueueStatisticsTotalPassPackets 
                    Counter64,                     
                hwXQoSPortQueueStatisticsTotalPassBytes
                    Counter64,             
                hwXQoSPortQueueStatisticsTotalDiscardPackets 
                    Counter64, 
                hwXQoSPortQueueStatisticsTotalDiscardBytes    
                    Counter64,
                hwXQoSPortQueueStatisticsDropTailDiscardPackets
                    Counter64,
                hwXQoSPortQueueStatisticsDropTailDiscardBytes
                    Counter64,
                hwXQoSPortQueueStatisticsWredDiscardPackets
                    Counter64,
                hwXQoSPortQueueStatisticsWredDiscardBytes
                    Counter64,
                hwXQoSPortQueueStatisticsPassPacketsRate
                    Counter64,
                hwXQoSPortQueueStatisticsPassBytesRate
                    Counter64,
                hwXQoSPortQueueStatisticsDiscardPacketsRate
                    Counter64,
                hwXQoSPortQueueStatisticsDiscardBytesRate
                    Counter64,
                hwXQoSPortQueueStatisticsDropTailDiscardPacketsRate
                    Counter64,  
                hwXQoSPortQueueStatisticsDropTailDiscardBytesRate
                    Counter64,
                hwXQoSPortQueueStatisticsWredDiscardPacketsRate
                    Counter64,
                hwXQoSPortQueueStatisticsWredDiscardBytesRate
                    Counter64,
                hwXQoSPortQueueStatisticsTrafficTowardThisPort
                    Counter64,
                hwXQoSPortQueueStatisticsPhysicalBandwidthOfPortQoS
                    Counter64,
                hwXQoSPortQueueStatisticsQueuePercentage   
	                Integer32, 
-- BEGIN: Added by l00248629, 2013/12/13
                hwXQoSPortQueueStatisticsTotalPackets
                    Counter64,
                hwXQoSPortQueueStatisticsTotalBytes
                    Counter64
-- END: Added by l00248629, 2013/12/13                                                 
                }

      hwXQoSPortQueueStatisticsInterfaceIndex  OBJECT-TYPE
            SYNTAX   InterfaceIndex
            MAX-ACCESS read-only
            STATUS current
            DESCRIPTION
            " This object indicates the interface index. "     
            ::= { hwXQoSPortQueueStatisticsEntry 1 }
       
       
      
      hwXQoSPortQueueStatisticsDirection  OBJECT-TYPE
            SYNTAX INTEGER
              {
                inbound(1),
                outbound(2) 
              }
            MAX-ACCESS read-only
            STATUS current
            DESCRIPTION
            " This object indicates the direction where statistics are queried.
              The value can be:
              1: inbound
              2: outbound  "
            ::= { hwXQoSPortQueueStatisticsEntry 2 }
 
      hwXQoSPortQueueStatisticsQueueIndex  OBJECT-TYPE
            SYNTAX INTEGER
              {
                be(1),
                af1(2), 
                af2(3),
                af3(4),
                af4(5),
                ef(6),
                cs6(7),
                cs7(8)
               }
            MAX-ACCESS read-only
            STATUS current
            DESCRIPTION
            " This object indicates the priority of a class queue where statistics are queried.
            The value can be:
            1 be
            2 af1
            3 af2
            4 af3
            5 af4
            6 ef
            7 cs6
            8 cs7
            9 total        
            "
            ::= { hwXQoSPortQueueStatisticsEntry 3 }
       
        
      hwXQoSPortQueueStatisticsReset  OBJECT-TYPE
            SYNTAX INTEGER 
            {
                reset(1)
            }
            MAX-ACCESS read-create
            STATUS current
            DESCRIPTION
            " This object indicates the statistics are reset.  "    
            ::= { hwXQoSPortQueueStatisticsEntry 4 }   
       
    
      hwXQoSPortQueueStatisticsTotalPassPackets OBJECT-TYPE
            SYNTAX  Counter64
            MAX-ACCESS read-only
            STATUS current
            DESCRIPTION
            " This object indicates the number of passed packets. "    
            ::= { hwXQoSPortQueueStatisticsEntry 5 }   
            
            
      hwXQoSPortQueueStatisticsTotalPassBytes OBJECT-TYPE
            SYNTAX  Counter64
            MAX-ACCESS read-only
            STATUS current
            DESCRIPTION
            " This object indicates the number of  passed bytes. "    
            ::= { hwXQoSPortQueueStatisticsEntry 6 }      


      hwXQoSPortQueueStatisticsTotalDiscardPackets OBJECT-TYPE
            SYNTAX  Counter64
            MAX-ACCESS read-only
            STATUS current
            DESCRIPTION
            " This object indicates the number of discarded packets. "    
            ::= { hwXQoSPortQueueStatisticsEntry 7 }    


      hwXQoSPortQueueStatisticsTotalDiscardBytes OBJECT-TYPE
            SYNTAX  Counter64
            MAX-ACCESS read-only
            STATUS current
            DESCRIPTION
            " This object indicates the number of discarded bytes. "    
            ::= { hwXQoSPortQueueStatisticsEntry 8 }   


      hwXQoSPortQueueStatisticsDropTailDiscardPackets OBJECT-TYPE
            SYNTAX  Counter64
            MAX-ACCESS read-only
            STATUS current
            DESCRIPTION
            " The value of this object identifies the number of discarded tail packets. "    
            ::= { hwXQoSPortQueueStatisticsEntry 9 }          


      hwXQoSPortQueueStatisticsDropTailDiscardBytes OBJECT-TYPE
            SYNTAX  Counter64
            MAX-ACCESS read-only
            STATUS current
            DESCRIPTION
            " The value of this object identifies the number of discarded tail bytes. "    
            ::= { hwXQoSPortQueueStatisticsEntry 10 }      


      hwXQoSPortQueueStatisticsWredDiscardPackets OBJECT-TYPE
            SYNTAX  Counter64
            MAX-ACCESS read-only
            STATUS current
            DESCRIPTION
            " The value of this object identifies the number of packets that are discarded by WRED. "    
            ::= { hwXQoSPortQueueStatisticsEntry 11 } 

 
      hwXQoSPortQueueStatisticsWredDiscardBytes OBJECT-TYPE
            SYNTAX  Counter64
            MAX-ACCESS read-only
            STATUS current
            DESCRIPTION
            " The value of this object identifies the number of bytes that are discarded by WRED. "    
            ::= { hwXQoSPortQueueStatisticsEntry 12 } 

      hwXQoSPortQueueStatisticsPassPacketsRate OBJECT-TYPE
            SYNTAX  Counter64
            MAX-ACCESS read-only
            STATUS current
            DESCRIPTION
            " This object indicates the packet pass rate. "    
            ::= { hwXQoSPortQueueStatisticsEntry 13 }  
 
 
      hwXQoSPortQueueStatisticsPassBytesRate OBJECT-TYPE
            SYNTAX  Counter64
            MAX-ACCESS read-only
            STATUS current
            DESCRIPTION
            " This object indicates the byte pass rate. "    
            ::= { hwXQoSPortQueueStatisticsEntry 14 }  
 
 
      hwXQoSPortQueueStatisticsDiscardPacketsRate OBJECT-TYPE
            SYNTAX  Counter64
            MAX-ACCESS read-only
            STATUS current
            DESCRIPTION
            " This object indicates the packet drop rate. "    
            ::= { hwXQoSPortQueueStatisticsEntry 15 }  

 
      hwXQoSPortQueueStatisticsDiscardBytesRate OBJECT-TYPE
            SYNTAX  Counter64
            MAX-ACCESS read-only
            STATUS current
            DESCRIPTION
            " This object indicates the byte drop rate. "    
            ::= { hwXQoSPortQueueStatisticsEntry 16 }  
 
 
      hwXQoSPortQueueStatisticsDropTailDiscardPacketsRate OBJECT-TYPE
            SYNTAX  Counter64
            MAX-ACCESS read-only
            STATUS current
            DESCRIPTION
            " This object indicates the tail packet discarding rate. "    
            ::= { hwXQoSPortQueueStatisticsEntry 17 }  
            
            
      hwXQoSPortQueueStatisticsDropTailDiscardBytesRate OBJECT-TYPE
            SYNTAX  Counter64
            MAX-ACCESS read-only
            STATUS current
            DESCRIPTION
            " This object indicates the tail byte discarding rate. "    
            ::= { hwXQoSPortQueueStatisticsEntry 18 }  


      hwXQoSPortQueueStatisticsWredDiscardPacketsRate OBJECT-TYPE
            SYNTAX  Counter64
            MAX-ACCESS read-only
            STATUS current
            DESCRIPTION
            " This object indicates the WRED packet discarding rate."    
            ::= { hwXQoSPortQueueStatisticsEntry 19 }  


      hwXQoSPortQueueStatisticsWredDiscardBytesRate OBJECT-TYPE
            SYNTAX  Counter64
            MAX-ACCESS read-only
            STATUS current
            DESCRIPTION
            " This object indicates the WRED byte discarding rate."    
            ::= { hwXQoSPortQueueStatisticsEntry 20 } 
            
      hwXQoSPortQueueStatisticsTrafficTowardThisPort OBJECT-TYPE
            SYNTAX  Counter64
            UNITS "bps"
            MAX-ACCESS read-only
            STATUS current
            DESCRIPTION
            " This object indicates the traffic which towards this port."    
            ::= { hwXQoSPortQueueStatisticsEntry 21 }  
      hwXQoSPortQueueStatisticsPhysicalBandwidthOfPortQoS OBJECT-TYPE
            SYNTAX  Counter64
            UNITS "bps"
            MAX-ACCESS read-only
            STATUS current
            DESCRIPTION
            " This object indicates the physical bandwidth of port QoS."    
            ::= { hwXQoSPortQueueStatisticsEntry 22 }  
      hwXQoSPortQueueStatisticsQueuePercentage OBJECT-TYPE
            SYNTAX Integer32 (0..100)
            MAX-ACCESS read-only
            STATUS current
            DESCRIPTION
                "This object indicates the queue percentage."
            ::= { hwXQoSPortQueueStatisticsEntry 23 }   
-- BEGIN: Added by l00248629, 2013/12/13
      hwXQoSPortQueueStatisticsTotalPackets OBJECT-TYPE
            SYNTAX  Counter64
            MAX-ACCESS read-only
            STATUS current
            DESCRIPTION
            " This object indicates the number of total packets."    
            ::= { hwXQoSPortQueueStatisticsEntry 24 } 
      hwXQoSPortQueueStatisticsTotalBytes OBJECT-TYPE
            SYNTAX  Counter64
            MAX-ACCESS read-only
            STATUS current
            DESCRIPTION
            " This object indicates the number of  total bytes."  
            ::= { hwXQoSPortQueueStatisticsEntry 25 } 
-- END: Added by l00248629, 2013/12/13                                                 
            
        hwXQoSMulBa8021pPhbCfgInfoTable OBJECT-TYPE
            SYNTAX SEQUENCE OF HwXQoSMulBa8021pPhbCfgInfoEntry
            MAX-ACCESS not-accessible
            STATUS current
            DESCRIPTION
                "Description."
            ::= { hwXQoSBaObjects 32 }

        
        hwXQoSMulBa8021pPhbCfgInfoEntry OBJECT-TYPE
            SYNTAX HwXQoSMulBa8021pPhbCfgInfoEntry
            MAX-ACCESS not-accessible
            STATUS current
            DESCRIPTION
                "Description."
            INDEX { hwXQoSMulBa8021pPhbIndex, hwXQoSMulBa8021pPri }
            ::= { hwXQoSMulBa8021pPhbCfgInfoTable 1 }

        
        HwXQoSMulBa8021pPhbCfgInfoEntry ::=
            SEQUENCE { 
                hwXQoSMulBa8021pPhbIndex
                    Integer32,
                hwXQoSMulBa8021pPri
                    Integer32,
                hwXQoSMulBa8021pPhbCos
                    INTEGER,
                hwXQoSMulBa8021pPhbRowStatus
                    RowStatus
             }


        hwXQoSMulBa8021pPhbIndex OBJECT-TYPE
            SYNTAX Integer32
            MAX-ACCESS read-only
            STATUS current
            DESCRIPTION
                "Description."
            ::= { hwXQoSMulBa8021pPhbCfgInfoEntry 1 }


        hwXQoSMulBa8021pPri OBJECT-TYPE
            SYNTAX Integer32 (0..7)
            MAX-ACCESS read-only
            STATUS current
            DESCRIPTION
                "Description."
            ::= { hwXQoSMulBa8021pPhbCfgInfoEntry 2 }


        hwXQoSMulBa8021pPhbCos OBJECT-TYPE
            SYNTAX INTEGER
                {
                be(1),
                af1(2),
                af2(3),
                af3(4),
                af4(5),
                ef(6),
                cs6(7),
                cs7(8)
                }
            MAX-ACCESS read-write
            STATUS current
            DESCRIPTION
                "Description."
            ::= { hwXQoSMulBa8021pPhbCfgInfoEntry 3 }


        hwXQoSMulBa8021pPhbRowStatus OBJECT-TYPE
            SYNTAX RowStatus
            MAX-ACCESS read-create
            STATUS current
            DESCRIPTION
                "Description."
            ::= { hwXQoSMulBa8021pPhbCfgInfoEntry 50 }


        hwXQoSMulDscpPhbCfgInfoTable OBJECT-TYPE
            SYNTAX SEQUENCE OF HwXQoSMulDscpPhbCfgInfoEntry
            MAX-ACCESS not-accessible
            STATUS current
            DESCRIPTION
                "Description."
            ::= { hwXQoSBaObjects 33 }


        hwXQoSMulDscpPhbCfgInfoEntry OBJECT-TYPE
            SYNTAX HwXQoSMulDscpPhbCfgInfoEntry
            MAX-ACCESS not-accessible
            STATUS current
            DESCRIPTION
                "Description."
            INDEX { hwXQoSMulBaDscpPhbIndex, hwXQoSMulBaDscpPri }
            ::= { hwXQoSMulDscpPhbCfgInfoTable 1 }


        HwXQoSMulDscpPhbCfgInfoEntry ::=
            SEQUENCE { 
                hwXQoSMulBaDscpPhbIndex
                    Integer32,
                hwXQoSMulBaDscpPri
                    Integer32,
                hwXQoSMulBaDscpPhbCos
                    INTEGER,
                hwXQoSMulBaDscpPhbRowStatus
                    RowStatus
             }


        hwXQoSMulBaDscpPhbIndex OBJECT-TYPE
            SYNTAX Integer32
            MAX-ACCESS read-only
            STATUS current
            DESCRIPTION
                "Description."
            ::= { hwXQoSMulDscpPhbCfgInfoEntry 1 }


        hwXQoSMulBaDscpPri OBJECT-TYPE
            SYNTAX Integer32 (0..63)
            MAX-ACCESS read-only
            STATUS current
            DESCRIPTION
                "Description."
            ::= { hwXQoSMulDscpPhbCfgInfoEntry 2 }


        hwXQoSMulBaDscpPhbCos OBJECT-TYPE
            SYNTAX INTEGER
                {
                be(1),
                af1(2),
                af2(3),
                af3(4),
                af4(5),
                ef(6),
                cs6(7),
                cs7(8)
                }
            MAX-ACCESS read-write
            STATUS current
            DESCRIPTION
                "Description."
            ::= { hwXQoSMulDscpPhbCfgInfoEntry 3 }


        hwXQoSMulBaDscpPhbRowStatus OBJECT-TYPE
            SYNTAX RowStatus
            MAX-ACCESS read-create
            STATUS current
            DESCRIPTION
                "Description."
            ::= { hwXQoSMulDscpPhbCfgInfoEntry 50 }


        hwXQoSBaUserPriPhbCfgInfoTable OBJECT-TYPE
            SYNTAX SEQUENCE OF HwXQoSBaUserPriPhbCfgInfoEntry
            MAX-ACCESS not-accessible
            STATUS current
            DESCRIPTION
                "Description."
            ::= { hwXQoSBaObjects 34 }


        hwXQoSBaUserPriPhbCfgInfoEntry OBJECT-TYPE
            SYNTAX HwXQoSBaUserPriPhbCfgInfoEntry
            MAX-ACCESS not-accessible
            STATUS current
            DESCRIPTION
                "Description."
            INDEX { hwXQoSDSUserPriIndex, hwXQoSUserPriPhbPri }
            ::= { hwXQoSBaUserPriPhbCfgInfoTable 1 }


        HwXQoSBaUserPriPhbCfgInfoEntry ::=
            SEQUENCE { 
                hwXQoSDSUserPriIndex
                    Integer32,
                hwXQoSUserPriPhbPri
                    Integer32,
                hwXQoSUserPriPhbCos
                    INTEGER,
                hwXQoSUserPriPhbColour
                    INTEGER,
                hwXQoSUserPriPhbRowStatus
                    RowStatus
             }


        hwXQoSDSUserPriIndex OBJECT-TYPE
            SYNTAX Integer32
            MAX-ACCESS read-only
            STATUS current
            DESCRIPTION
                "Description."
            ::= { hwXQoSBaUserPriPhbCfgInfoEntry 1 }


        hwXQoSUserPriPhbPri OBJECT-TYPE
            SYNTAX Integer32 (0..7)
            MAX-ACCESS read-only
            STATUS current
            DESCRIPTION
                "Description."
            ::= { hwXQoSBaUserPriPhbCfgInfoEntry 2 }


        hwXQoSUserPriPhbCos OBJECT-TYPE
            SYNTAX INTEGER
                {
                be(1),
                af1(2),
                af2(3),
                af3(4),
                af4(5),
                ef(6),
                cs6(7),
                cs7(8)
                }
            MAX-ACCESS read-write
            STATUS current
            DESCRIPTION
                "Description."
            ::= { hwXQoSBaUserPriPhbCfgInfoEntry 3 }


        hwXQoSUserPriPhbColour OBJECT-TYPE
            SYNTAX INTEGER
                {
                green(1),
                yellow(2),
                red(3)
                }
            MAX-ACCESS read-write
            STATUS current
            DESCRIPTION
                "Description."
            ::= { hwXQoSBaUserPriPhbCfgInfoEntry 4 }


        hwXQoSUserPriPhbRowStatus OBJECT-TYPE
            SYNTAX RowStatus
            MAX-ACCESS read-create
            STATUS current
            DESCRIPTION
                "Description."
            ::= { hwXQoSBaUserPriPhbCfgInfoEntry 50 }


        hwXQoSAAATrustCfgInfoTable OBJECT-TYPE
            SYNTAX SEQUENCE OF HwXQoSAAATrustCfgInfoEntry
            MAX-ACCESS not-accessible
            STATUS current
            DESCRIPTION
                "Description."
            ::= { hwXQoSBaObjects 35 }


        hwXQoSAAATrustCfgInfoEntry OBJECT-TYPE
            SYNTAX HwXQoSAAATrustCfgInfoEntry
            MAX-ACCESS not-accessible
            STATUS current
            DESCRIPTION
                "Description."
            INDEX { hwXQoSAaaDomainName }
            ::= { hwXQoSAAATrustCfgInfoTable 1 }


        HwXQoSAAATrustCfgInfoEntry ::=
            SEQUENCE { 
                hwXQoSAaaDomainName
                    OCTET STRING,
                hwXQoSAAADsDomainName
                    OCTET STRING,
                hwXQoSAAADsRowStatus
                    RowStatus
             }


        hwXQoSAaaDomainName OBJECT-TYPE
            SYNTAX OCTET STRING (SIZE (1..31))
            MAX-ACCESS read-only
            STATUS current
            DESCRIPTION
                "Description."
            ::= { hwXQoSAAATrustCfgInfoEntry 1 }


        hwXQoSAAADsDomainName OBJECT-TYPE
            SYNTAX OCTET STRING (SIZE (1..8))
            MAX-ACCESS read-write
            STATUS current
            DESCRIPTION
                "Description."
            ::= { hwXQoSAAATrustCfgInfoEntry 2 }

        hwXQoSAAADsRowStatus OBJECT-TYPE
            SYNTAX RowStatus
            MAX-ACCESS read-create
            STATUS current
            DESCRIPTION
                "Description."
            ::= { hwXQoSAAATrustCfgInfoEntry 50 }

       hwXQoSAAATrust8021pInfoTable OBJECT-TYPE
            SYNTAX SEQUENCE OF HwXQoSAAATrust8021pInfoEntry
            MAX-ACCESS not-accessible
            STATUS current
            DESCRIPTION
                "Description."
            ::= { hwXQoSBaObjects 36 }


        hwXQoSAAATrust8021pInfoEntry OBJECT-TYPE
            SYNTAX HwXQoSAAATrust8021pInfoEntry
            MAX-ACCESS not-accessible
            STATUS current
            DESCRIPTION
                "Description."
            INDEX { hwXQoSAaaDomainName }
            ::= { hwXQoSAAATrust8021pInfoTable 1 }


        HwXQoSAAATrust8021pInfoEntry ::=
            SEQUENCE { 
                hwXQoSAAADs8021P
                    INTEGER,
                hwXQoSAAADs8021pRowStatus
                    RowStatus
             }


        hwXQoSAAADs8021P OBJECT-TYPE
            SYNTAX INTEGER
                {
                disable(1),
                enable(2)
                }
            MAX-ACCESS read-write
            STATUS current
            DESCRIPTION
                "Description."
            ::= { hwXQoSAAATrust8021pInfoEntry 1 }


        hwXQoSAAADs8021pRowStatus OBJECT-TYPE
            SYNTAX RowStatus
            MAX-ACCESS read-create
            STATUS current
            DESCRIPTION
                "Description."
            ::= { hwXQoSAAATrust8021pInfoEntry 50 }

--   Interface view command
    hwXQoSIfActionObjects OBJECT IDENTIFIER ::= { hwXQoSObjects 2 }

    
--    CAR
    hwXQoSIfCarCfgInfoTable OBJECT-TYPE
        SYNTAX SEQUENCE OF HwXQoSIfCarCfgInfoEntry
        MAX-ACCESS not-accessible
        STATUS current
        DESCRIPTION
            "A table of CAR feature configuration information."
        ::= { hwXQoSIfActionObjects 1 }

    
    hwXQoSIfCarCfgInfoEntry OBJECT-TYPE
        SYNTAX HwXQoSIfCarCfgInfoEntry
        MAX-ACCESS not-accessible
        STATUS current
        DESCRIPTION
            "CAR Configuration Information Entry."
        INDEX { hwXQoSIfCarCfgIfIndex, hwXQoSIfCarVlanID, hwXQoSIfCarDirection }
        ::= { hwXQoSIfCarCfgInfoTable 1 }

    
    HwXQoSIfCarCfgInfoEntry ::=
        SEQUENCE { 
            hwXQoSIfCarCfgIfIndex
                Integer32,
            hwXQoSIfCarVlanID
                Integer32,
            hwXQoSIfCarDirection
                DirectionType,
            hwXQoSIfCarCir
                Integer32,
            hwXQoSIfCarCbs
                Integer32,
            hwXQoSIfCarEbs
                Integer32,
            hwXQoSIfCarPir
                Integer32,
            hwXQoSIfCarPbs
                Integer32,
            hwXQoSIfCarGreenAction
                CarAction,
            hwXQoSIfCarGreenRemarkValue
                Integer32,
            hwXQoSIfCarYellowAction
                CarAction,
            hwXQoSIfCarYellowRemarkValue
                Integer32,
            hwXQoSIfCarRedAction
                CarAction,
            hwXQoSIfCarRedRemarkValue
                Integer32,
            hwXQoSIfCarRowStatus
                RowStatus,
            hwXQoSIfCarCirEx
                Unsigned32,
            hwXQoSIfCarCbsEx
                Unsigned32,
            hwXQoSIfCarPirEx
                Unsigned32,
            hwXQoSIfCarPbsEx
                Unsigned32
         }

    hwXQoSIfCarCfgIfIndex OBJECT-TYPE
        SYNTAX Integer32
        MAX-ACCESS read-only
        STATUS current
        DESCRIPTION
            "Interface Index, equal to ifIndex."
        ::= { hwXQoSIfCarCfgInfoEntry 1 }

    hwXQoSIfCarVlanID OBJECT-TYPE
        SYNTAX Integer32 (0 | 1..4095)
        MAX-ACCESS read-only
        STATUS current
        DESCRIPTION
            "Vlan ID.
            -1 can't be set.
            0 is the default value"
        ::= { hwXQoSIfCarCfgInfoEntry 2 }

    hwXQoSIfCarDirection OBJECT-TYPE
        SYNTAX DirectionType
        MAX-ACCESS read-only
        STATUS current
        DESCRIPTION
            "Policy direction:
            inbound (1)
            outbound (2)"
        ::= { hwXQoSIfCarCfgInfoEntry 3 }

    hwXQoSIfCarCir OBJECT-TYPE
        SYNTAX Integer32
        MAX-ACCESS read-create
        STATUS current
        DESCRIPTION
            "Committed Information Rate. Unit: kbps.
            software QoS: 8..155000
            hardware QoS: 100..10000000"
        ::= { hwXQoSIfCarCfgInfoEntry 4 }

    
    hwXQoSIfCarCbs OBJECT-TYPE
        SYNTAX Integer32
        MAX-ACCESS read-create
        STATUS current
        DESCRIPTION
            "Committed Burst Size. Unit: byte
            software QoS: 1875..19375000 
            hardware QoS: 64..33554432"
        ::= { hwXQoSIfCarCfgInfoEntry 5 }

    
    hwXQoSIfCarEbs OBJECT-TYPE
        SYNTAX Integer32
        MAX-ACCESS read-create
        STATUS current
        DESCRIPTION
            "Excess Burst Size. Unit: byte. 0..19375000
            Only software QoS support this node.
            -1 is returned only when getting value from hardware QoS.
            -1 can't be set."
        DEFVAL { 0 }
        ::= { hwXQoSIfCarCfgInfoEntry 6 }

    
    hwXQoSIfCarPir OBJECT-TYPE
        SYNTAX Integer32
        MAX-ACCESS read-create
        STATUS current
        DESCRIPTION
            "Peak Information Rate. Unit: kbps. 100..10000000
            Only hardware QoS support this node.
            -1 is returned only when getting value from software QoS.
            -1 can't be set.
            0 is the default value"
        ::= { hwXQoSIfCarCfgInfoEntry 7 }

    
    hwXQoSIfCarPbs OBJECT-TYPE
        SYNTAX Integer32
        MAX-ACCESS read-create
        STATUS current
        DESCRIPTION
            "Peak Burst Size. Unit: byte.
            64..33554432.
            Only hardware QoS support this node.
            -1 is returned only when getting value from software QoS.
            -1 can't be set.
            0 is the default value"
        ::= { hwXQoSIfCarCfgInfoEntry 8 }

    
    hwXQoSIfCarGreenAction OBJECT-TYPE
        SYNTAX CarAction
        MAX-ACCESS read-create
        STATUS current
        DESCRIPTION
            "Green Action:
            pass (1)
            discard (2)                
            remark IP Precedence (3)
            remark DSCP (4)
            remark MPLS EXP (5)
            remark (6)
            Hardware QoS : pass,discard,remark.
            Software QoS : pass,discard,remark IP Precedence,remark DSCP,remark MPLS EXP.
            "
        DEFVAL { pass }
        ::= { hwXQoSIfCarCfgInfoEntry 9 }

    
    hwXQoSIfCarGreenRemarkValue OBJECT-TYPE
        SYNTAX Integer32 (-1 | 0..63)
        MAX-ACCESS read-create
        STATUS current
        DESCRIPTION
            "The value is to remark When green action is remarking.
            For remarking DSCP, the range is 0~63;
            For remarking IP Precedence and MPLS EXP, the range is 0~7;
            Only software QoS support this node.
            -1 is returned only when getting value from hardware QoS or when action being pass,discard of software QoS.
            -1 can't be set."
        ::= { hwXQoSIfCarCfgInfoEntry 10 }

    
    hwXQoSIfCarYellowAction OBJECT-TYPE
        SYNTAX CarAction
        MAX-ACCESS read-create
        STATUS current
        DESCRIPTION
            "Yellow Action:
            unavailable(-1)
            pass (1)
            discard (2)
            remark IP Precedence (3)
            remark DSCP (4)
            remark MPLS EXP (5)
            remark(6)
            Only hardware QoS support this node.Hardware QoS support pass,discard,remark.
            -1 is returned only when getting value from software QoS.
            -1 can't be set."
        ::= { hwXQoSIfCarCfgInfoEntry 11 }

    
    hwXQoSIfCarYellowRemarkValue OBJECT-TYPE
        SYNTAX Integer32 (-1 | 0..63)
        MAX-ACCESS read-create
        STATUS current
        DESCRIPTION
            "The value is to remark When yellow action is remarking.
            For remarking DSCP, the range is 0~63;
            For remarking IP Precedence and MPLS EXP, the range is 0~7;
            Only software QoS support this node.
            -1 is returned only when getting value from hardware QoS or when action being pass,discard of software QoS.
            -1 can't be set."
        ::= { hwXQoSIfCarCfgInfoEntry 12 }

    
    hwXQoSIfCarRedAction OBJECT-TYPE
        SYNTAX CarAction
        MAX-ACCESS read-create
        STATUS current
        DESCRIPTION
            "Red Action:
            pass (1)
            discard (2)                
            remark IP Precedence (3)
            remark DSCP (4)
            remark MPLS EXP (5)
            remark (6)
            Hardware QoS : pass,discard,remark.
            Software QoS : pass,discard,remark IP Precedence,remark DSCP,remark MPLS EXP.
            "
        DEFVAL { discard }
        ::= { hwXQoSIfCarCfgInfoEntry 13 }

    
    hwXQoSIfCarRedRemarkValue OBJECT-TYPE
        SYNTAX Integer32 (-1 | 0..63)
        MAX-ACCESS read-create
        STATUS current
        DESCRIPTION
            "The value is to remark When red action is remarking.
            For remarking DSCP, the range is 0~63;
            For remarking IP Precedence and MPLS EXP, the range is 0~7;
            Only software QoS support this node.
            -1 is returned only when getting value from hardware QoS or when action being pass,discard of software QoS.
            -1 can't be set."
        ::= { hwXQoSIfCarCfgInfoEntry 14 }

    hwXQoSIfCarRowStatus OBJECT-TYPE
        SYNTAX RowStatus
        MAX-ACCESS read-create
        STATUS current
        DESCRIPTION
            "RowStatus. Three actions are used: active,
            createAndGo, destroy"
        ::= { hwXQoSIfCarCfgInfoEntry 15 }

    hwXQoSIfCarCirEx OBJECT-TYPE
        SYNTAX Unsigned32
        MAX-ACCESS read-create
        STATUS current
        DESCRIPTION
            "Committed Information Rate. Unit: kbps."
        ::= { hwXQoSIfCarCfgInfoEntry 16 }

    hwXQoSIfCarCbsEx OBJECT-TYPE
        SYNTAX Unsigned32
        MAX-ACCESS read-create
        STATUS current
        DESCRIPTION
            "Committed Burst Size. Unit: byte."
        ::= { hwXQoSIfCarCfgInfoEntry 17 }
    
    hwXQoSIfCarPirEx OBJECT-TYPE
        SYNTAX Unsigned32
        MAX-ACCESS read-create
        STATUS current
        DESCRIPTION
            "Peak Information Rate. Unit: kbps."
        ::= { hwXQoSIfCarCfgInfoEntry 18 }

    hwXQoSIfCarPbsEx OBJECT-TYPE
        SYNTAX Unsigned32
        MAX-ACCESS read-create
        STATUS current
        DESCRIPTION
            "Peak Burst Size. Unit: byte."
        ::= { hwXQoSIfCarCfgInfoEntry 19 }
		
--    mirror behavior
    hwXQoSIfMirrorCfgInfoTable OBJECT-TYPE
        SYNTAX SEQUENCE OF HwXQoSIfMirrorCfgInfoEntry
        MAX-ACCESS not-accessible
        STATUS current
        DESCRIPTION
            "A table of Mirror configuration information."
        ::= { hwXQoSIfActionObjects 2 }

    
    hwXQoSIfMirrorCfgInfoEntry OBJECT-TYPE
        SYNTAX HwXQoSIfMirrorCfgInfoEntry
        MAX-ACCESS not-accessible
        STATUS current
        DESCRIPTION
            "Mirror Configuration Information Entry."
        INDEX { hwXQoSIfMirrorCfgIfIndex, hwXQoSIfMirrorCfgVlanID, hwXQoSIfMirrorDirection }
        ::= { hwXQoSIfMirrorCfgInfoTable 1 }

    
    HwXQoSIfMirrorCfgInfoEntry ::=
        SEQUENCE { 
            hwXQoSIfMirrorCfgIfIndex
                Integer32,
            hwXQoSIfMirrorCfgVlanID
                Integer32,
            hwXQoSIfMirrorDirection
                DirectionType,
            hwXQoSIfMirrorObserveIndex
                Integer32,
            hwXQoSIfMirrorRowStatus
                RowStatus
         }

    hwXQoSIfMirrorCfgIfIndex OBJECT-TYPE
        SYNTAX Integer32
        MAX-ACCESS read-only
        STATUS current
        DESCRIPTION
            "Interface Index, equal to ifIndex."
        ::= { hwXQoSIfMirrorCfgInfoEntry 1 }

    hwXQoSIfMirrorCfgVlanID OBJECT-TYPE
        SYNTAX Integer32 (0 | 1..4095)
        MAX-ACCESS read-only
        STATUS current
        DESCRIPTION
            "Vlan ID.
            -1 can't be set.
            0 is the default value"
        ::= { hwXQoSIfMirrorCfgInfoEntry 2 }

    hwXQoSIfMirrorDirection OBJECT-TYPE
        SYNTAX DirectionType
        MAX-ACCESS read-only
        STATUS current
        DESCRIPTION
            "Policy direction:
            inbound (1)
            outbound (2)"
        ::= { hwXQoSIfMirrorCfgInfoEntry 3 }

    hwXQoSIfMirrorObserveIndex OBJECT-TYPE
        SYNTAX Integer32 (1..16)
        MAX-ACCESS read-create
        STATUS current
        DESCRIPTION
            "The mirror observe port number"
        ::= { hwXQoSIfMirrorCfgInfoEntry 4 }

    hwXQoSIfMirrorRowStatus OBJECT-TYPE
        SYNTAX RowStatus
        MAX-ACCESS read-create
        STATUS current
        DESCRIPTION
            "RowStatus. Three actions are used: active,
            createAndGo, destroy"
        ::= { hwXQoSIfMirrorCfgInfoEntry 5 }

    
--    Urpf behavior
    hwXQoSIfUrpfCfgInfoTable OBJECT-TYPE
        SYNTAX SEQUENCE OF HwXQoSIfUrpfCfgInfoEntry
        MAX-ACCESS not-accessible
        STATUS current
        DESCRIPTION
            "A table of Urpf configuration information."
        ::= { hwXQoSIfActionObjects 3 }

    
    hwXQoSIfUrpfCfgInfoEntry OBJECT-TYPE
        SYNTAX HwXQoSIfUrpfCfgInfoEntry
        MAX-ACCESS not-accessible
        STATUS current
        DESCRIPTION
            "Urpf Configuration Information Entry."
        INDEX { hwXQoSIfUrpfCfgIfIndex, hwXQoSIfUrpfCfgVlanID }
        ::= { hwXQoSIfUrpfCfgInfoTable 1 }

    
    HwXQoSIfUrpfCfgInfoEntry ::=
        SEQUENCE { 
            hwXQoSIfUrpfCfgIfIndex
                Integer32,
            hwXQoSIfUrpfCfgVlanID
                Integer32,
            hwXQoSIfUrpfCtrlType
                UrpfCtrlType,
            hwXQoSIfUrpfAllowDefault
                INTEGER,
            hwXQoSIfUrpfRowStatus
                RowStatus
         }

    hwXQoSIfUrpfCfgIfIndex OBJECT-TYPE
        SYNTAX Integer32
        MAX-ACCESS read-only
        STATUS current
        DESCRIPTION
            "The value of this object identifies the interface index.The object has no default value."
        ::= { hwXQoSIfUrpfCfgInfoEntry 1 }

    hwXQoSIfUrpfCfgVlanID OBJECT-TYPE
        SYNTAX Integer32 (0 | 1..4095)
        MAX-ACCESS read-only
        STATUS current
        DESCRIPTION
            "Vlan ID.
            -1 can't be set.
            0 is the default value"
        ::= { hwXQoSIfUrpfCfgInfoEntry 2 }

    hwXQoSIfUrpfCtrlType OBJECT-TYPE
        SYNTAX UrpfCtrlType
        MAX-ACCESS read-create
        STATUS current
        DESCRIPTION
            "The value of this object identifies the control type of URPF.The value can be either of the following:Strict(1)
,Loose(2).The object has no default value."
        ::= { hwXQoSIfUrpfCfgInfoEntry 3 }

    
    hwXQoSIfUrpfAllowDefault OBJECT-TYPE
        SYNTAX INTEGER
            {
            false(0),
            true(1)
            }
        MAX-ACCESS read-create
        STATUS current
        DESCRIPTION
            "The value of this object identifies whether the default route is allowed according to URPF.The value can be either of the following:
            0: indicates that the default route is not allowed.
            1: indicates that the default route is allowed.
The object has no default value."
        ::= { hwXQoSIfUrpfCfgInfoEntry 4 }

    hwXQoSIfUrpfRowStatus OBJECT-TYPE
        SYNTAX RowStatus
        MAX-ACCESS read-create
        STATUS current
        DESCRIPTION
            "This value of this object identifies the row status.The value can be any of the following:Active(1),CreateAndGo(4),Destroy(6).The object has no default value."
        ::= { hwXQoSIfUrpfCfgInfoEntry 5 }

    
--    Sampling behavior
    hwXQoSIfSamplingCfgInfoTable OBJECT-TYPE
        SYNTAX SEQUENCE OF HwXQoSIfSamplingCfgInfoEntry
        MAX-ACCESS not-accessible
        STATUS current
        DESCRIPTION
            "A table of Sampling configuration information."
        ::= { hwXQoSIfActionObjects 4 }

    
    hwXQoSIfSamplingCfgInfoEntry OBJECT-TYPE
        SYNTAX HwXQoSIfSamplingCfgInfoEntry
        MAX-ACCESS not-accessible
        STATUS current
        DESCRIPTION
            "Sampling Configuration Information Entry."
        INDEX { hwXQoSIfSamplingIfIndex, hwXQoSIfSamplingVlanID, hwXQoSIfSamplingDirection }
        ::= { hwXQoSIfSamplingCfgInfoTable 1 }

    
    HwXQoSIfSamplingCfgInfoEntry ::=
        SEQUENCE { 
            hwXQoSIfSamplingIfIndex
                Integer32,
            hwXQoSIfSamplingVlanID
                Integer32,
            hwXQoSIfSamplingDirection
                DirectionType,
            hwXQoSIfSamplingType
                SampleType,
            hwXQoSIfSamplingNum
                Integer32,
            hwXQoSIfSamplingRowStatus
                RowStatus
         }

    hwXQoSIfSamplingIfIndex OBJECT-TYPE
        SYNTAX Integer32
        MAX-ACCESS read-only
        STATUS current
        DESCRIPTION
            "Indicates the index of a sampling interface."
        ::= { hwXQoSIfSamplingCfgInfoEntry 1 }

    hwXQoSIfSamplingVlanID OBJECT-TYPE
        SYNTAX Integer32 (0 | 1..4095)
        MAX-ACCESS read-only
        STATUS current
        DESCRIPTION
            "Indicates the VLAN ID of a sampling interface."
        ::= { hwXQoSIfSamplingCfgInfoEntry 2 }

    hwXQoSIfSamplingDirection OBJECT-TYPE
        SYNTAX DirectionType
        MAX-ACCESS read-only
        STATUS current
        DESCRIPTION
            "Indicates whether the interface is an inbound interface or an outbound interface.
            inbound (1)
            outbound (2)"
        ::= { hwXQoSIfSamplingCfgInfoEntry 3}

    hwXQoSIfSamplingType OBJECT-TYPE
        SYNTAX SampleType
        MAX-ACCESS read-create
        STATUS current
        DESCRIPTION
            "Indicates the sampling type.
            Fix-packets(1)
            Fix-time(2)
            Random-packets(3)
            Random-time(4)
            "
        ::= { hwXQoSIfSamplingCfgInfoEntry 4 }

    
    hwXQoSIfSamplingNum OBJECT-TYPE
        SYNTAX Integer32 (1..65535)
        MAX-ACCESS read-create
        STATUS current
        DESCRIPTION
            "Indicates the sampling parameter."
        ::= { hwXQoSIfSamplingCfgInfoEntry 5 }

    hwXQoSIfSamplingRowStatus OBJECT-TYPE
        SYNTAX RowStatus
        MAX-ACCESS read-create
        STATUS current
        DESCRIPTION
            "Indicates the row status. Three actions are used: active,
            createAndGo, destroy"
        ::= { hwXQoSIfSamplingCfgInfoEntry 6 }

    
--    lr
    hwXQoSIfLrCfgInfoTable OBJECT-TYPE
        SYNTAX SEQUENCE OF HwXQoSIfLrCfgInfoEntry
        MAX-ACCESS not-accessible
        STATUS current
        DESCRIPTION
            "A table of lr configuration information."
        ::= { hwXQoSIfActionObjects 5 }

    
    hwXQoSIfLrCfgInfoEntry OBJECT-TYPE
        SYNTAX HwXQoSIfLrCfgInfoEntry
        MAX-ACCESS not-accessible
        STATUS current
        DESCRIPTION
            "Lr Configuration Information Entry."
        INDEX { hwXQoSIfLrCfgIfIndex, hwXQoSIfLrCfgVlanID }
        ::= { hwXQoSIfLrCfgInfoTable 1 }

    
    HwXQoSIfLrCfgInfoEntry ::=
        SEQUENCE { 
            hwXQoSIfLrCfgIfIndex
                Integer32,
            hwXQoSIfLrCfgVlanID
                Integer32,
            hwXQoSIfLrCir
                Integer32,            
            hwXQoSIfLrRowStatus
                RowStatus,
            hwXQoSIfLrCbs
                Integer32, 
            hwXQoSIfInPhyBandwidth
                Integer32, 
            hwXQoSIfOutPhyBandwidth
                Integer32,
            hwXQoSIfInActualBandwidth
                OCTET STRING,
            hwXQoSIfOutActualBandwidth
                OCTET STRING              
         }

    hwXQoSIfLrCfgIfIndex OBJECT-TYPE
        SYNTAX Integer32
        MAX-ACCESS read-only
        STATUS current
        DESCRIPTION
            "The value of this object identifies the interface index.The object has no default value."
        ::= { hwXQoSIfLrCfgInfoEntry 1 }

    hwXQoSIfLrCfgVlanID OBJECT-TYPE
        SYNTAX Integer32 (0 | 1..4095)
        MAX-ACCESS read-only
        STATUS current
        DESCRIPTION
            "Vlan ID.
            -1 can't be set.
            0 is the default value"
        ::= { hwXQoSIfLrCfgInfoEntry 2 }

    hwXQoSIfLrCir OBJECT-TYPE
        SYNTAX Integer32
        MAX-ACCESS read-create
        STATUS current
        DESCRIPTION
            "This value of this object identifies CIR.The value ranges from 1 to the bandwidth of the interface.The object has no default value."
        ::= { hwXQoSIfLrCfgInfoEntry 3 }
 
    hwXQoSIfLrRowStatus OBJECT-TYPE
        SYNTAX RowStatus
        MAX-ACCESS read-create
        STATUS current
        DESCRIPTION
            "This value of this object identifies the row status.The value can be any of the following:CreateAndGo(4),
Destroy(6),Active(1).The object has no default value."
        ::= { hwXQoSIfLrCfgInfoEntry 4 }

     hwXQoSIfLrCbs OBJECT-TYPE
        SYNTAX Integer32
        MAX-ACCESS read-create
        STATUS current
        DESCRIPTION
            "The lr cbs Unit: byte."
        ::= { hwXQoSIfLrCfgInfoEntry 5 }
         
     hwXQoSIfInPhyBandwidth OBJECT-TYPE
        SYNTAX Integer32
        MAX-ACCESS read-only
        STATUS current
        DESCRIPTION
            "The inbound physical bandwidth Unit: bps."
        ::= { hwXQoSIfLrCfgInfoEntry 6 }  
        
       hwXQoSIfOutPhyBandwidth OBJECT-TYPE
        SYNTAX Integer32
        MAX-ACCESS read-only
        STATUS current
        DESCRIPTION
            "The outbound physical bandwidth Unit: bps."
        ::= { hwXQoSIfLrCfgInfoEntry 7 }      
        
      hwXQoSIfInActualBandwidth OBJECT-TYPE
        SYNTAX OCTET STRING (SIZE (1..31))
        MAX-ACCESS read-only
        STATUS current
        DESCRIPTION
            "The inbound actual bandwidth Unit: bps."
        ::= { hwXQoSIfLrCfgInfoEntry 8 }
        
      hwXQoSIfOutActualBandwidth OBJECT-TYPE
        SYNTAX OCTET STRING (SIZE (1..31))
        MAX-ACCESS read-only
        STATUS current
        DESCRIPTION
            "The outbound actual bandwidth Unit: bps."
        ::= { hwXQoSIfLrCfgInfoEntry 9 }   
                    
--    queue
    hwXQoSIfQueueCfgInfoTable OBJECT-TYPE
        SYNTAX SEQUENCE OF HwXQoSIfQueueCfgInfoEntry
        MAX-ACCESS not-accessible
        STATUS current
        DESCRIPTION
            "A table of Queue feature configuration information."
        ::= { hwXQoSIfActionObjects 6 }

    
    hwXQoSIfQueueCfgInfoEntry OBJECT-TYPE
        SYNTAX HwXQoSIfQueueCfgInfoEntry
        MAX-ACCESS not-accessible
        STATUS current
        DESCRIPTION
            "CAR Configuration Information Entry."
        INDEX { hwXQoSIfQueueCfgIfIndex, hwXQoSIfQueueCfgVlanID, hwXQoSIfQueueDirection, hwXQoSIfQueueCfgCosType }
        ::= { hwXQoSIfQueueCfgInfoTable 1 }

    
    HwXQoSIfQueueCfgInfoEntry ::=
        SEQUENCE { 
            hwXQoSIfQueueCfgIfIndex
                Integer32,
            hwXQoSIfQueueCfgVlanID
                Integer32,
            hwXQoSIfQueueDirection
                DirectionType,
            hwXQoSIfQueueCfgCosType
                CosType,
            hwXQoSIfQueuePriority
                Integer32,
            hwXQoSIfQueueCir
                Integer32,
            hwXQoSIfQueuePir
                Integer32,
            hwXQoSIfQueueWeight
                Integer32,
            hwXQoSIfQueueMode
                INTEGER,          
            hwXQoSIfQueueRowStatus
                RowStatus
         }

    hwXQoSIfQueueCfgIfIndex OBJECT-TYPE
        SYNTAX Integer32
        MAX-ACCESS read-only
        STATUS current
        DESCRIPTION
            "The value of this object identifies the interface index.The default value is 0."
        ::= { hwXQoSIfQueueCfgInfoEntry 1 }

    hwXQoSIfQueueCfgVlanID OBJECT-TYPE
        SYNTAX Integer32 (0 | 1..4095)
        MAX-ACCESS read-only
        STATUS current
        DESCRIPTION
            "Vlan ID.
            -1 can't be set.
            0 is the default value"
        ::= { hwXQoSIfQueueCfgInfoEntry 2 }

    hwXQoSIfQueueDirection OBJECT-TYPE
        SYNTAX DirectionType
        MAX-ACCESS read-only
        STATUS current
        DESCRIPTION
            "The value of this object identifies the direction of policy application.The value can be either of the following:Inbound(1),Outbound(2)."
        ::= { hwXQoSIfQueueCfgInfoEntry 3 }

    hwXQoSIfQueueCfgCosType OBJECT-TYPE
        SYNTAX CosType
        MAX-ACCESS read-only
        STATUS current
        DESCRIPTION
            "The value of this object identifies CoS of the queue.The value ranges from 0 to 7. CS(7),CS(6),EF(5),AF(4),AF(3)
,AF(2),AF(1),BE(0).The default value is BE(0). "
        ::= { hwXQoSIfQueueCfgInfoEntry 4 }  
        
    hwXQoSIfQueuePriority OBJECT-TYPE
        SYNTAX Integer32 
        MAX-ACCESS read-write
        STATUS current
        DESCRIPTION
            "The queue priority of PQ queue mode. "
        ::= { hwXQoSIfQueueCfgInfoEntry 5 } 

    
    hwXQoSIfQueueCir OBJECT-TYPE
        SYNTAX Integer32 
        MAX-ACCESS read-write
        STATUS current
        DESCRIPTION
            "The value of this object identifies CIR of the queue.The value ranges from 0 to 10000000.The object has no default value."
        ::= { hwXQoSIfQueueCfgInfoEntry 6 }

    
    hwXQoSIfQueuePir OBJECT-TYPE
        SYNTAX Integer32 
        MAX-ACCESS read-write
        STATUS current
        DESCRIPTION
            "The value of this object identifies PIR of the queue.The value ranges from 0 to 10000000.The object has no default value."
        ::= { hwXQoSIfQueueCfgInfoEntry 7 }  
        
     hwXQoSIfQueueWeight OBJECT-TYPE
        SYNTAX Integer32
        MAX-ACCESS read-write
        STATUS current
        DESCRIPTION
            "The queue weight of wrr or drr queue mode"
        ::= { hwXQoSIfQueueCfgInfoEntry 8 } 
        
    hwXQoSIfQueueMode OBJECT-TYPE
        SYNTAX INTEGER {
            pq(1), 
            wrr(3),
            wfq(4),
            default(5),
            drr(6)
           }
        MAX-ACCESS read-write
        STATUS current
        DESCRIPTION
            "The value of this object identifies the scheduling mode for queues.The value can be either of the following:
pq(1),wrr(3),wfq(4),default(5).The NE40E can support either of the following value:pq(1),wfq(4).The default value is default(5). "
        ::= { hwXQoSIfQueueCfgInfoEntry 9 }

    hwXQoSIfQueueRowStatus OBJECT-TYPE
        SYNTAX RowStatus
        MAX-ACCESS read-create
        STATUS current
        DESCRIPTION
            "This value of this object identifies the row status.The value can be any of the following:CreateAndGo(4), Destroy(6),Active(1).The object has no default value."
        ::= { hwXQoSIfQueueCfgInfoEntry 10 }

    
--    observe port
    hwXQoSIfObserveCfgInfoTable OBJECT-TYPE
        SYNTAX SEQUENCE OF HwXQoSIfObserveCfgInfoEntry
        MAX-ACCESS not-accessible
        STATUS current
        DESCRIPTION
            "A table of Observe configuration information."
        ::= { hwXQoSIfActionObjects 7 }

    
    hwXQoSIfObserveCfgInfoEntry OBJECT-TYPE
        SYNTAX HwXQoSIfObserveCfgInfoEntry
        MAX-ACCESS not-accessible
        STATUS current
        DESCRIPTION
            "Observe Configuration Information Entry."
        INDEX { hwXQoSIfObserveIndex }
        ::= { hwXQoSIfObserveCfgInfoTable 1 }

    
    HwXQoSIfObserveCfgInfoEntry ::=
        SEQUENCE { 
            hwXQoSIfObserveIndex
                Integer32,
            hwXQoSIfObserveIfIndex
                Integer32,
            hwXQoSIfObserveRowStatus
                RowStatus
         }

    hwXQoSIfObserveIndex OBJECT-TYPE
        SYNTAX Integer32
        MAX-ACCESS read-only
        STATUS current
        DESCRIPTION
            "The Observe number "
        ::= { hwXQoSIfObserveCfgInfoEntry 1 }

    
    hwXQoSIfObserveIfIndex OBJECT-TYPE
        SYNTAX Integer32
        MAX-ACCESS read-create
        STATUS current
        DESCRIPTION
            "Interface Index, equal to ifIndex."
        ::= { hwXQoSIfObserveCfgInfoEntry 2 }

    
    hwXQoSIfObserveRowStatus OBJECT-TYPE
        SYNTAX RowStatus
        MAX-ACCESS read-create
        STATUS current
        DESCRIPTION
            "RowStatus. Three actions are used: active,
            createAndGo, destroy"
        ::= { hwXQoSIfObserveCfgInfoEntry 3 }

-- Wred
    hwXQoSIfWredCfgInfoTable OBJECT-TYPE
        SYNTAX SEQUENCE OF HwXQoSIfWredCfgInfoEntry
        MAX-ACCESS not-accessible
        STATUS current
        DESCRIPTION
            "A table of Wred configuration information."
        ::= { hwXQoSIfActionObjects 8 }

    
    hwXQoSIfWredCfgInfoEntry OBJECT-TYPE
        SYNTAX HwXQoSIfWredCfgInfoEntry
        MAX-ACCESS not-accessible
        STATUS current
        DESCRIPTION
            "Wred Configuration Information Entry."
        INDEX { hwXQoSIfWredQueueIndex, hwXQoSIfWredDirection}
        ::= { hwXQoSIfWredCfgInfoTable 1 }

    
    HwXQoSIfWredCfgInfoEntry ::=
        SEQUENCE { 
            hwXQoSIfWredQueueIndex
                Integer32, 
            hwXQoSIfWredDirection
                DirectionType,
            hwXQoSIfWredType
                INTEGER,
            hwXQoSIfWredLowlimit
                Integer32,            
            hwXQoSIfWredHighlimit
                Integer32,
            hwXQoSIfWredDiscardProbability
                Integer32,
            hwXQoSIfWredHighDiscardProbability
                Integer32,
            hwXQoSIfWredRowStatus
                RowStatus
         }

    hwXQoSIfWredQueueIndex OBJECT-TYPE
        SYNTAX Integer32(0..7)
        MAX-ACCESS read-only
        STATUS current
        DESCRIPTION
            "The Wred queue index "
        ::= { hwXQoSIfWredCfgInfoEntry 1 }
    
    hwXQoSIfWredDirection OBJECT-TYPE
        SYNTAX DirectionType
        MAX-ACCESS read-only
        STATUS current
        DESCRIPTION
            "Policy direction:
            inbound (1)
            outbound (2)"
        ::= { hwXQoSIfWredCfgInfoEntry 2 }

    hwXQoSIfWredType OBJECT-TYPE
        SYNTAX INTEGER
        {
            ipPrec(1),
            dscp(2)
        }
        MAX-ACCESS read-write
        STATUS current
        DESCRIPTION
            "IP-Prec Based (1)
            DSCP Based (2)"
        DEFVAL { ip-precbased }
        ::= { hwXQoSIfWredCfgInfoEntry 3 }
                            
    hwXQoSIfWredLowlimit OBJECT-TYPE
        SYNTAX Integer32
        MAX-ACCESS read-create
        STATUS current
        DESCRIPTION
            "The Wred Lowlimit. unit:packet"
        ::= { hwXQoSIfWredCfgInfoEntry 4 }
 
     hwXQoSIfWredHighlimit OBJECT-TYPE
        SYNTAX Integer32
        MAX-ACCESS read-create
        STATUS current
        DESCRIPTION
            "The Wred Highlimit.unit:packet"
        ::= { hwXQoSIfWredCfgInfoEntry 5 }

    hwXQoSIfWredDiscardProbability OBJECT-TYPE
        SYNTAX Integer32(1..100)
        MAX-ACCESS read-create
        STATUS current
        DESCRIPTION
            "The Wred Discard Probability."
        ::= { hwXQoSIfWredCfgInfoEntry 6 }
        
    hwXQoSIfWredHighDiscardProbability OBJECT-TYPE
        SYNTAX Integer32(1..100)
        MAX-ACCESS read-create
        STATUS current
        DESCRIPTION
            "The Wred High Discard Probability."
        ::= { hwXQoSIfWredCfgInfoEntry 7 }
            
    hwXQoSIfWredRowStatus OBJECT-TYPE
        SYNTAX RowStatus
        MAX-ACCESS read-create
        STATUS current
        DESCRIPTION
            "RowStatus. Three actions are used: active,
            createAndGo, destroy"
        ::= { hwXQoSIfWredCfgInfoEntry 8 }

-- 8021p-local-precedence-map
    hwXQoSIf8021PMapCfgInfoTable OBJECT-TYPE
        SYNTAX SEQUENCE OF HwXQoSIf8021PMapCfgInfoEntry
        MAX-ACCESS not-accessible
        STATUS current
        DESCRIPTION
            "A table of 8021PMap configuration information."
        ::= { hwXQoSIfActionObjects 9 }

    
    hwXQoSIf8021PMapCfgInfoEntry OBJECT-TYPE
        SYNTAX HwXQoSIf8021PMapCfgInfoEntry
        MAX-ACCESS not-accessible
        STATUS current
        DESCRIPTION
            "8021PMap Configuration Information Entry."
        INDEX { hwXQoSIf8021PMap8021PValue }
        ::= { hwXQoSIf8021PMapCfgInfoTable 1 }

    
    HwXQoSIf8021PMapCfgInfoEntry ::=
        SEQUENCE { 
            hwXQoSIf8021PMap8021PValue
                Integer32,
            hwXQoSIf8021PMapLocalPrecedence
                Integer32,            
            hwXQoSIf8021PMapRowStatus
                RowStatus
         }

    hwXQoSIf8021PMap8021PValue OBJECT-TYPE
        SYNTAX Integer32(0..7)
        MAX-ACCESS read-only
        STATUS current
        DESCRIPTION
            "The 8021PMap 802.1p value "
        ::= { hwXQoSIf8021PMapCfgInfoEntry 1 }

    
    hwXQoSIf8021PMapLocalPrecedence OBJECT-TYPE
        SYNTAX Integer32(0..7)
        MAX-ACCESS read-create
        STATUS current
        DESCRIPTION
            "The 8021PMap Local Precedence."
        ::= { hwXQoSIf8021PMapCfgInfoEntry 2 }

            
    hwXQoSIf8021PMapRowStatus OBJECT-TYPE
        SYNTAX RowStatus
        MAX-ACCESS read-create
        STATUS current
        DESCRIPTION
            "RowStatus. Three actions are used: active,
            createAndGo, destroy"
        ::= { hwXQoSIf8021PMapCfgInfoEntry 3 }

-- mpls exp-exp-map
    hwXQoSIfMplsExpMapCfgInfoTable OBJECT-TYPE
        SYNTAX SEQUENCE OF HwXQoSIfMplsExpMapCfgInfoEntry
        MAX-ACCESS not-accessible
        STATUS current
        DESCRIPTION
            "A table of mpls exp-exp-map configuration information."
        ::= { hwXQoSIfActionObjects 10 }

    
    hwXQoSIfMplsExpMapCfgInfoEntry OBJECT-TYPE
        SYNTAX HwXQoSIfMplsExpMapCfgInfoEntry
        MAX-ACCESS not-accessible
        STATUS current
        DESCRIPTION
            "mpls exp-exp-map Configuration Information Entry."
        INDEX { hwXQoSIfMplsExpMapIfIndex, hwXQoSIfMplsExpMapInbound }
        ::= { hwXQoSIfMplsExpMapCfgInfoTable 1 }

    
    HwXQoSIfMplsExpMapCfgInfoEntry ::=
        SEQUENCE { 
            hwXQoSIfMplsExpMapIfIndex
                Integer32,
            hwXQoSIfMplsExpMapInbound
                Integer32,
            hwXQoSIfMplsExpMapOutbound
                Integer32,            
            hwXQoSIfMplsExpMapRowStatus
                RowStatus
         }

    hwXQoSIfMplsExpMapIfIndex OBJECT-TYPE
        SYNTAX Integer32
        MAX-ACCESS read-only
        STATUS current
        DESCRIPTION
            "Interface Index, equal to ifIndex."
        ::= { hwXQoSIfMplsExpMapCfgInfoEntry 1 }

    hwXQoSIfMplsExpMapInbound OBJECT-TYPE
        SYNTAX Integer32(0..7)
        MAX-ACCESS read-only
        STATUS current
        DESCRIPTION
            "The mpls exp-exp-map inbound value"
        ::= { hwXQoSIfMplsExpMapCfgInfoEntry 2 }

    
    hwXQoSIfMplsExpMapOutbound OBJECT-TYPE
        SYNTAX Integer32(0..7)
        MAX-ACCESS read-create
        STATUS current
        DESCRIPTION
            "The mpls exp-exp-map outbound value"
        ::= { hwXQoSIfMplsExpMapCfgInfoEntry 3 }

    hwXQoSIfMplsExpMapRowStatus OBJECT-TYPE
        SYNTAX RowStatus
        MAX-ACCESS read-create
        STATUS current
        DESCRIPTION
            "RowStatus. Three actions are used: active,
            createAndGo, destroy"
        ::= { hwXQoSIfMplsExpMapCfgInfoEntry 4 }
        
--    Default priority
    hwXQoSIfDefaultPriorityCfgInfoTable OBJECT-TYPE
        SYNTAX SEQUENCE OF HwXQoSIfDefaultPriorityCfgInfoEntry
        MAX-ACCESS not-accessible
        STATUS current
        DESCRIPTION
            "A table of default priority configuration information."
        ::= { hwXQoSIfActionObjects 11}

    
    hwXQoSIfDefaultPriorityCfgInfoEntry OBJECT-TYPE
        SYNTAX HwXQoSIfDefaultPriorityCfgInfoEntry
        MAX-ACCESS not-accessible
        STATUS current
        DESCRIPTION
            "Default priority Configuration Information Entry."
        INDEX { hwXQoSIfDefaultPriorityIfIndex, hwXQoSIfDefaultPriorityVlanID }
        ::= { hwXQoSIfDefaultPriorityCfgInfoTable 1 }

    
    HwXQoSIfDefaultPriorityCfgInfoEntry ::=
        SEQUENCE { 
            hwXQoSIfDefaultPriorityIfIndex
                Integer32,
            hwXQoSIfDefaultPriorityVlanID
                Integer32,
            hwXQoSIfDefaultPriorityValue
                Integer32,
            hwXQoSIfDefaultPriorityRowStatus
                RowStatus
         }

    hwXQoSIfDefaultPriorityIfIndex OBJECT-TYPE
        SYNTAX Integer32
        MAX-ACCESS read-only
        STATUS current
        DESCRIPTION
            "Interface Index, equal to ifIndex."
        ::= { hwXQoSIfDefaultPriorityCfgInfoEntry 1 }

    hwXQoSIfDefaultPriorityVlanID OBJECT-TYPE
        SYNTAX Integer32 (0 | 1..4094)
        MAX-ACCESS read-create
        STATUS current
        DESCRIPTION
            "Vlan ID.
            -1 can't be set.
            0 is the default value"
        ::= { hwXQoSIfDefaultPriorityCfgInfoEntry 2 }

    hwXQoSIfDefaultPriorityValue OBJECT-TYPE
        SYNTAX Integer32 (0..7)
        MAX-ACCESS read-create
        STATUS current
        DESCRIPTION
            "The default priority value "
        ::= { hwXQoSIfDefaultPriorityCfgInfoEntry 3 }

    hwXQoSIfDefaultPriorityRowStatus OBJECT-TYPE
        SYNTAX RowStatus
        MAX-ACCESS read-create
        STATUS current
        DESCRIPTION
            "RowStatus. Three actions are used: active,
            createAndGo, destroy"
    ::= { hwXQoSIfDefaultPriorityCfgInfoEntry 4 }
    
    -- 1.3.6.1.4.1.2011.5.25.32.4.1.2.12
    hwXQoSIfSoftCarTable OBJECT-TYPE
        SYNTAX SEQUENCE OF HwXQoSIfSoftCarEntry
        MAX-ACCESS not-accessible
        STATUS current
        DESCRIPTION
        "A table of interface software CAR  configuration  information."
        ::= { hwXQoSIfActionObjects 12 }
    
    -- 1.3.6.1.4.1.2011.5.25.32.4.1.2.12.1
    hwXQoSIfSoftCarEntry OBJECT-TYPE
        SYNTAX HwXQoSIfSoftCarEntry
        MAX-ACCESS not-accessible
        STATUS current
        DESCRIPTION
        "Interface software CAR  configuration  information entry."
        INDEX { hwXQoSIfSoftCarIfIndex,hwXQoSIfSoftCarDirection }
        ::= { hwXQoSIfSoftCarTable 1 }
    
    HwXQoSIfSoftCarEntry ::=
        SEQUENCE { 
            hwXQoSIfSoftCarIfIndex
                Integer32,
            hwXQoSIfSoftCarDirection
                DirectionType,    
            hwXQoSIfSoftCarCarIndex
                Integer32,
            hwXQoSIfSoftCarRowStatus
                RowStatus
         }

    -- 1.3.6.1.4.1.2011.5.25.32.4.1.2.12.1.1
    hwXQoSIfSoftCarIfIndex OBJECT-TYPE
        SYNTAX Integer32
            MAX-ACCESS not-accessible
        STATUS current
        DESCRIPTION
        "Interface index,equal ifIndex."
        ::= { hwXQoSIfSoftCarEntry 1 }
        
    -- 1.3.6.1.4.1.2011.5.25.32.4.1.2.12.1.2
    hwXQoSIfSoftCarDirection OBJECT-TYPE
        SYNTAX DirectionType
            MAX-ACCESS not-accessible
        STATUS current
        DESCRIPTION
            "Policy direction:
            inbound (1)
            outbound (2)"
        ::= { hwXQoSIfSoftCarEntry 2 }    
    
    -- 1.3.6.1.4.1.2011.5.25.32.4.1.2.12.1.3
    hwXQoSIfSoftCarCarIndex OBJECT-TYPE
            SYNTAX Integer32 (0..65534)
            MAX-ACCESS read-create
        STATUS current
        DESCRIPTION
        "Car index,refers to hwXQoSCpcarIndex."
        ::= { hwXQoSIfSoftCarEntry 3 }
    
    -- 1.3.6.1.4.1.2011.5.25.32.4.1.2.12.1.4
    hwXQoSIfSoftCarRowStatus OBJECT-TYPE
        SYNTAX RowStatus
        MAX-ACCESS read-create
        STATUS current
        DESCRIPTION
            "RowStatus. Three actions are used: active,
            createAndGo, destroy."
        ::= { hwXQoSIfSoftCarEntry 4 } 
        
-- local-precedence-queue-map
    hwXQoSIfLocalPrecedenceQueueMapTable OBJECT-TYPE
        SYNTAX SEQUENCE OF HwXQoSIfLocalPrecedenceQueueMapEntry
        MAX-ACCESS not-accessible
        STATUS current
        DESCRIPTION
            "A table of local precedence to queue map information."
        ::= { hwXQoSIfActionObjects 13 }

    
    hwXQoSIfLocalPrecedenceQueueMapEntry OBJECT-TYPE
        SYNTAX HwXQoSIfLocalPrecedenceQueueMapEntry
        MAX-ACCESS not-accessible
        STATUS current
        DESCRIPTION
            "local precedence to queue map Information Entry."
        INDEX { hwXQoSIfLocPreQueMapIfIndex, hwXQoSIfLocPreQueMapPreValue}
        ::= { hwXQoSIfLocalPrecedenceQueueMapTable 1 }
    
    HwXQoSIfLocalPrecedenceQueueMapEntry ::=
        SEQUENCE { 
            hwXQoSIfLocPreQueMapIfIndex
                Integer32,
            hwXQoSIfLocPreQueMapPreValue
               Integer32,             
            hwXQoSIfLocPreQueMapCosType
                CosType,
            hwXQoSIfLocPreQueMapRowStatus
                RowStatus
         }

    hwXQoSIfLocPreQueMapIfIndex OBJECT-TYPE
        SYNTAX Integer32
        MAX-ACCESS read-only
        STATUS current
        DESCRIPTION
            "interface index "
        ::= { hwXQoSIfLocalPrecedenceQueueMapEntry 1 }
  
    hwXQoSIfLocPreQueMapPreValue OBJECT-TYPE
        SYNTAX Integer32(0..7)
        MAX-ACCESS read-only
        STATUS current
        DESCRIPTION
            " Local precedence value."
        ::= { hwXQoSIfLocalPrecedenceQueueMapEntry 2 }

    hwXQoSIfLocPreQueMapCosType OBJECT-TYPE
        SYNTAX CosType
        MAX-ACCESS read-write
        STATUS current
        DESCRIPTION
            "queue index"
        ::= { hwXQoSIfLocalPrecedenceQueueMapEntry 3 }  
                  
    hwXQoSIfLocPreQueMapRowStatus OBJECT-TYPE
        SYNTAX RowStatus
        MAX-ACCESS read-create
        STATUS current
        DESCRIPTION
            "RowStatus. Three actions are used: active,
            createAndGo, destroy"
        ::= { hwXQoSIfLocalPrecedenceQueueMapEntry  4 }
        
    hwXQoSIfScheduleModeCfgInfoTable OBJECT-TYPE
        SYNTAX SEQUENCE OF HwXQoSIfScheduleModeCfgInfoEntry
        MAX-ACCESS not-accessible
        STATUS current
        DESCRIPTION
            "A table of Schedule mode configuration information."
        ::= { hwXQoSIfActionObjects 14}

    
    hwXQoSIfScheduleModeCfgInfoEntry OBJECT-TYPE
        SYNTAX HwXQoSIfScheduleModeCfgInfoEntry
        MAX-ACCESS not-accessible
        STATUS current
        DESCRIPTION
            "Schedule mode Configuration Information Entry."
        INDEX { hwXQoSIfScheduleModeIfIndex }
        ::= { hwXQoSIfScheduleModeCfgInfoTable 1 }
    
    HwXQoSIfScheduleModeCfgInfoEntry ::=
        SEQUENCE { 
            hwXQoSIfScheduleModeIfIndex
                Integer32,
            hwXQoSIfModeType
                INTEGER,
            hwXQoSIfScheduleModeRowStatus
                RowStatus
         }

    hwXQoSIfScheduleModeIfIndex OBJECT-TYPE
        SYNTAX Integer32
        MAX-ACCESS not-accessible
        STATUS current
        DESCRIPTION
            "Interface Index, equal to ifIndex."
        ::= { hwXQoSIfScheduleModeCfgInfoEntry 1 }

    hwXQoSIfModeType OBJECT-TYPE
        SYNTAX INTEGER   
            {
             pqWfq(1),
             pq(2),
             wfq(3)
            }
        MAX-ACCESS read-create
        STATUS current
        DESCRIPTION
            "Schedule mode are PQ+WFQ(1), PQ(2) or WFQ(3)."
        ::= { hwXQoSIfScheduleModeCfgInfoEntry 2 }
    
    hwXQoSIfScheduleModeRowStatus OBJECT-TYPE
        SYNTAX RowStatus
        MAX-ACCESS read-create
        STATUS current
        DESCRIPTION
            "RowStatus. Three actions are used: active,
            createAndGo, destroy"
    ::= { hwXQoSIfScheduleModeCfgInfoEntry 3 }

    hwXQoSIfHQOSPriCfgInfoTable OBJECT-TYPE
        SYNTAX SEQUENCE OF HwXQoSIfHQOSPriCfgInfoEntry
        MAX-ACCESS not-accessible
        STATUS current
        DESCRIPTION
            "HQOS priority configure configuration table. "
        ::= { hwXQoSIfActionObjects 15}

    
    hwXQoSIfHQOSPriCfgInfoEntry OBJECT-TYPE
        SYNTAX HwXQoSIfHQOSPriCfgInfoEntry
        MAX-ACCESS not-accessible
        STATUS current
        DESCRIPTION
            "HQOS priority Configuration Information Entry."
        INDEX { hwXQoSIfHqosPriIfIndex }
        ::= { hwXQoSIfHQOSPriCfgInfoTable 1 }
    
    HwXQoSIfHQOSPriCfgInfoEntry ::=
        SEQUENCE { 
            hwXQoSIfHqosPriIfIndex
                Integer32,
            hwXQoSIfHqosPriority
                INTEGER,
            hwXQoSIfHqosPriRowStatus
                RowStatus
         }

    hwXQoSIfHqosPriIfIndex OBJECT-TYPE
        SYNTAX Integer32
        MAX-ACCESS not-accessible
        STATUS current
        DESCRIPTION
            "Interface Index, equal to ifIndex."
        ::= { hwXQoSIfHQOSPriCfgInfoEntry 1 }

    hwXQoSIfHqosPriority OBJECT-TYPE
        SYNTAX INTEGER { be(1),af1(2),af2(3),af3(4),af4(5),ef(6),cs6(7),cs7(8)}
        MAX-ACCESS read-create
        STATUS current
        DESCRIPTION
            " be(1),af1(2),af2(3),af3(4),af4(5),ef(6),cs6(7),cs7(8)"
        ::= { hwXQoSIfHQOSPriCfgInfoEntry 2 }
    
    hwXQoSIfHqosPriRowStatus OBJECT-TYPE
        SYNTAX RowStatus
        MAX-ACCESS read-create
        STATUS current
        DESCRIPTION
            "RowStatus. Three actions are used: active,
            createAndGo, destroy"
    ::= { hwXQoSIfHQOSPriCfgInfoEntry 3 }
    
    hwXQoSIfOutboundMulticastCfgInfoTable OBJECT-TYPE
        SYNTAX SEQUENCE OF HwXQoSIfOutboundMulticastCfgInfoEntry
        MAX-ACCESS not-accessible
        STATUS current
        DESCRIPTION
            "Multicast outbound bandwidth table."
        ::= { hwXQoSIfActionObjects 16}

    
    hwXQoSIfOutboundMulticastCfgInfoEntry OBJECT-TYPE
        SYNTAX HwXQoSIfOutboundMulticastCfgInfoEntry
        MAX-ACCESS not-accessible
        STATUS current
        DESCRIPTION
            "Multicast outbound bandwidth Configuration Information Entry."
        INDEX { hwXQoSIfOutMulticastIfIndex }
        ::= { hwXQoSIfOutboundMulticastCfgInfoTable 1 }

    
    HwXQoSIfOutboundMulticastCfgInfoEntry ::=
        SEQUENCE { 
            hwXQoSIfOutMulticastIfIndex
                Integer32,
            hwXQoSIfUnicastWeightValue 
                Integer32,
            hwXQoSIfMulticastWeightValue
                Integer32,
            hwXQoSIfOutMulticastRowStatus
                RowStatus
         }

    hwXQoSIfOutMulticastIfIndex OBJECT-TYPE
        SYNTAX Integer32
        MAX-ACCESS not-accessible
        STATUS current
        DESCRIPTION
            "Interface Index, equal to ifIndex."
        ::= { hwXQoSIfOutboundMulticastCfgInfoEntry 1 }

    hwXQoSIfUnicastWeightValue OBJECT-TYPE
        SYNTAX Integer32 (0..15)
        MAX-ACCESS read-create
        STATUS current
        DESCRIPTION
            "Unicast weight value range(0~15)."
        ::= { hwXQoSIfOutboundMulticastCfgInfoEntry 2 }

    hwXQoSIfMulticastWeightValue OBJECT-TYPE
        SYNTAX Integer32 (0..15)
        MAX-ACCESS read-create
        STATUS current
        DESCRIPTION
            "Multicast weight value range(0~15). "
        ::= { hwXQoSIfOutboundMulticastCfgInfoEntry 3 }

    hwXQoSIfOutMulticastRowStatus OBJECT-TYPE
        SYNTAX RowStatus
        MAX-ACCESS read-create
        STATUS current
        DESCRIPTION
            "RowStatus. Three actions are used: active,
            createAndGo, destroy"
    ::= { hwXQoSIfOutboundMulticastCfgInfoEntry 4 }
    
--sRed
    hwXQoSIfSredCfgInfoTable OBJECT-TYPE
        SYNTAX SEQUENCE OF HwXQoSIfSredCfgInfoEntry
        MAX-ACCESS not-accessible
        STATUS current
        DESCRIPTION
            "A table of Sred configuration information."
        ::= { hwXQoSIfActionObjects 17 }

    hwXQoSIfSredCfgInfoEntry OBJECT-TYPE
        SYNTAX HwXQoSIfSredCfgInfoEntry
        MAX-ACCESS not-accessible
        STATUS current
        DESCRIPTION
            "Sred Configuration Information Entry."
        INDEX { hwXQoSIfSredQueueIndex }
        ::= { hwXQoSIfSredCfgInfoTable 1 }
    
    HwXQoSIfSredCfgInfoEntry ::=
        SEQUENCE {
            hwXQoSIfSredQueueIndex
                INTEGER, 
            hwXQoSIfSredRedStartDiscardPoint
                Integer32,
            hwXQoSIfSredRedDiscardProbability
                INTEGER,                            
            hwXQoSIfSredYellowStartDiscardPoint
                Integer32,
            hwXQoSIfSredYellowDiscardProbability
                INTEGER,
            hwXQoSIfSredRowStatus
                RowStatus
         }

    hwXQoSIfSredQueueIndex OBJECT-TYPE
        SYNTAX INTEGER
        {
        be(1),
        af1(2),
        af2(3),
        af3(4),
        af4(5),
        ef(6),
        cs6(7),
        cs7(8)        
        }
        MAX-ACCESS not-accessible
        STATUS current
        DESCRIPTION
            "The Sred queue index 
             be(1),
             af1(2),
             af2(3),
             af3(4),
             af4(5),
             ef(6),
             cs6(7),
             cs7(8)"
        ::= { hwXQoSIfSredCfgInfoEntry 1 }
                            
    hwXQoSIfSredRedStartDiscardPoint OBJECT-TYPE
        SYNTAX Integer32       
        MAX-ACCESS read-create
        STATUS current
        DESCRIPTION
            "The Sred Red Start Discard Point.unit:packet"
        ::= { hwXQoSIfSredCfgInfoEntry 2 }

    hwXQoSIfSredRedDiscardProbability OBJECT-TYPE
        SYNTAX INTEGER
        {
        drop1(1),
        drop2(2),
        drop3(3),
        drop4(4),
        drop5(5),
        drop6(6),
        drop7(7),
        drop8(8)
        }        
        MAX-ACCESS read-create
        STATUS current
        DESCRIPTION
            "The Sred Red Discard Probability.
             drop1(1) = 100%
             drop2(2) = 6.25%
             drop3(3) = 3.125%
             drop4(4) = 1.5625%
             drop5(5) = 0.78125%
             drop6(6) = 0.390625%
             drop7(7) = 0.1953125%
             drop8(8) = 0.09765625% "
        ::= { hwXQoSIfSredCfgInfoEntry 3 }
        
    hwXQoSIfSredYellowStartDiscardPoint OBJECT-TYPE
        SYNTAX Integer32
        MAX-ACCESS read-create
        STATUS current
        DESCRIPTION
            "The Sred Yellow Start Discard Point.unit:packet"
        ::= { hwXQoSIfSredCfgInfoEntry 4 }

    hwXQoSIfSredYellowDiscardProbability OBJECT-TYPE
        SYNTAX INTEGER
        {
        drop1(1),
        drop2(2),
        drop3(3),
        drop4(4),
        drop5(5),
        drop6(6),
        drop7(7),
        drop8(8)
        }          
        MAX-ACCESS read-create
        STATUS current
        DESCRIPTION
            "The Sred Yellow Discard Probability.
             drop1(1) = 100%
             drop2(2) = 6.25%
             drop3(3) = 3.125%
             drop4(4) = 1.5625%
             drop5(5) = 0.78125%
             drop6(6) = 0.390625%
             drop7(7) = 0.1953125%
             drop8(8) = 0.09765625% "
        ::= { hwXQoSIfSredCfgInfoEntry 5 }
            
    hwXQoSIfSredRowStatus OBJECT-TYPE
        SYNTAX RowStatus
        MAX-ACCESS read-create
        STATUS current
        DESCRIPTION
            "RowStatus. Three actions are used: active,
            createAndGo, destroy"
        ::= { hwXQoSIfSredCfgInfoEntry 6 }

--add at 2007-12-10
    hwXQosAtmTrafficQueueTable OBJECT-TYPE
    SYNTAX SEQUENCE OF HwXQosAtmTrafficQueueEntry
    MAX-ACCESS not-accessible
    STATUS current
    DESCRIPTION
        "The table provides traffic classification."
    ::= { hwXQoSIfActionObjects 18 }
    
    hwXQosAtmTrafficQueueEntry OBJECT-TYPE
        SYNTAX HwXQosAtmTrafficQueueEntry
        MAX-ACCESS not-accessible
        STATUS current
        DESCRIPTION
            "Traffic classification entry."
        INDEX { hwXQoSAtmTrafficQueueIfIndex }
        ::= { hwXQosAtmTrafficQueueTable 1 }
    
    HwXQosAtmTrafficQueueEntry ::=
        SEQUENCE { 
            hwXQoSAtmTrafficQueueIfIndex
                Unsigned32,
            hwXQoSAtmTrafficQueueServiceClass
                Integer32,
            hwXQoSAtmTrafficQueueRowStatus
                RowStatus
         }

    hwXQoSAtmTrafficQueueIfIndex OBJECT-TYPE
    SYNTAX Unsigned32
    MAX-ACCESS not-accessible
    STATUS current
    DESCRIPTION
        "Index of interface."
    ::= { hwXQosAtmTrafficQueueEntry 1 }
            
    hwXQoSAtmTrafficQueueServiceClass OBJECT-TYPE
    SYNTAX Integer32
    MAX-ACCESS read-create
    STATUS current
    DESCRIPTION
        "The service class of the ATM traffic queue."
    ::= { hwXQosAtmTrafficQueueEntry 2 }
            
    hwXQoSAtmTrafficQueueRowStatus OBJECT-TYPE
    SYNTAX RowStatus
    MAX-ACCESS read-create
    STATUS current
    DESCRIPTION
        "State of the row."
    ::= { hwXQosAtmTrafficQueueEntry 3 }
            
    hwXQoSAtmPvcServiceTypeTable OBJECT-TYPE
    SYNTAX SEQUENCE OF HwXQoSAtmPvcServiceTypeEntry
    MAX-ACCESS not-accessible
    STATUS current
    DESCRIPTION
        "The table provides ATM PVC service type."
    ::= { hwXQoSIfActionObjects 19 }
            
    hwXQoSAtmPvcServiceTypeEntry OBJECT-TYPE
    SYNTAX HwXQoSAtmPvcServiceTypeEntry
    MAX-ACCESS not-accessible
    STATUS current
    DESCRIPTION
        "ATM PVC service entry."
    INDEX { hwXQoSAtmPvcServiceTypeVpiIndex, hwXQoSAtmPvcServiceTypeVciIndex, hwXQoSAtmPvcServiceTypeIfIndex }
    ::= { hwXQoSAtmPvcServiceTypeTable 1 }
        
    HwXQoSAtmPvcServiceTypeEntry ::=
    SEQUENCE { 
        hwXQoSAtmPvcServiceTypeIfIndex
            Unsigned32,
        hwXQoSAtmPvcServiceTypeVpiIndex
            Unsigned32,
        hwXQoSAtmPvcServiceTypeVciIndex
            Unsigned32,
        hwXQoSAtmPvcNameServiceTypeIndex
            OCTET STRING,
        hwXQoSAtmPvcServiceType
            Integer32,
        hwXQoSAtmPvcPcr
            Integer32,
        hwXQoSAtmPvcCdvt
            Integer32,
        hwXQoSAtmPvcVbrScr
            Integer32,
        hwXQoSAtmPvcVbrMbs
            Integer32,
        hwXQoSAtmPvcRowStatus
            RowStatus
     }
     
     hwXQoSAtmPvcServiceTypeIfIndex OBJECT-TYPE
         SYNTAX Unsigned32
         MAX-ACCESS not-accessible
         STATUS current
         DESCRIPTION
             "Index of interface."
         ::= { hwXQoSAtmPvcServiceTypeEntry 1 }
            
    hwXQoSAtmPvcServiceTypeVpiIndex OBJECT-TYPE
        SYNTAX Unsigned32
        MAX-ACCESS not-accessible
        STATUS current
        DESCRIPTION
            "VPI for PVC."
        ::= { hwXQoSAtmPvcServiceTypeEntry 2 }
            
    hwXQoSAtmPvcServiceTypeVciIndex OBJECT-TYPE
        SYNTAX Unsigned32
        MAX-ACCESS not-accessible
        STATUS current
        DESCRIPTION
            "VCI for PVC."
        ::= { hwXQoSAtmPvcServiceTypeEntry 3 }
            
    hwXQoSAtmPvcNameServiceTypeIndex OBJECT-TYPE
        SYNTAX OCTET STRING
        MAX-ACCESS read-only
        STATUS current
        DESCRIPTION
            "Name for PVC."
        ::= { hwXQoSAtmPvcServiceTypeEntry 4 }
    
    hwXQoSAtmPvcServiceType OBJECT-TYPE
        SYNTAX Integer32
        MAX-ACCESS read-create
        STATUS current
        DESCRIPTION
            "Type of the service."
        ::= { hwXQoSAtmPvcServiceTypeEntry 5 }
    
    hwXQoSAtmPvcPcr OBJECT-TYPE
        SYNTAX Integer32
        MAX-ACCESS read-create
        STATUS current
        DESCRIPTION
            "Peak rate for sending ATM cells."
        ::= { hwXQoSAtmPvcServiceTypeEntry 6 }
    
    hwXQoSAtmPvcCdvt OBJECT-TYPE
        SYNTAX Integer32
        MAX-ACCESS read-create
        STATUS current
        DESCRIPTION
            "Tolerance of cell delay changes."
        ::= { hwXQoSAtmPvcServiceTypeEntry 7 }
    
    hwXQoSAtmPvcVbrScr OBJECT-TYPE
        SYNTAX Integer32
        MAX-ACCESS read-create
        STATUS current
        DESCRIPTION
            "Sustainable Rate for Sending ATM Cells."
        ::= { hwXQoSAtmPvcServiceTypeEntry 8 }
    
    hwXQoSAtmPvcVbrMbs OBJECT-TYPE
        SYNTAX Integer32
        MAX-ACCESS read-create
        STATUS current
        DESCRIPTION
            "Maximum Burst Size for Sending ATM Cells."
        ::= { hwXQoSAtmPvcServiceTypeEntry 9 }
    
    hwXQoSAtmPvcRowStatus OBJECT-TYPE
        SYNTAX RowStatus
        MAX-ACCESS read-create
        STATUS current
        DESCRIPTION
            "State of the row."
        ::= { hwXQoSAtmPvcServiceTypeEntry 10 }
        
--Shaping
    hwXQoSIfShapingCfgInfoTable OBJECT-TYPE
        SYNTAX SEQUENCE OF HwXQoSIfShapingCfgInfoEntry
        MAX-ACCESS not-accessible
        STATUS current
        DESCRIPTION
            "A table of Shaping configuration information."
        ::= { hwXQoSIfActionObjects 20 }

    hwXQoSIfShapingCfgInfoEntry OBJECT-TYPE
        SYNTAX HwXQoSIfShapingCfgInfoEntry
        MAX-ACCESS not-accessible
        STATUS current
        DESCRIPTION
            "Shaping Configuration Information Entry."
        INDEX { hwXQoSIfShapingIfIndex,hwXQoSIfShapingQueueIndex}
        ::= { hwXQoSIfShapingCfgInfoTable 1 }
    
    HwXQoSIfShapingCfgInfoEntry ::=
        SEQUENCE { 
            hwXQoSIfShapingIfIndex
                Integer32, 
            hwXQoSIfShapingQueueIndex
                INTEGER, 
            hwXQoSIfShapingQueueCir
                Integer32,
            hwXQoSIfShapingQueuePir
                Integer32,
            hwXQoSIfShapingRowStatus
                RowStatus
         }
           
    hwXQoSIfShapingIfIndex OBJECT-TYPE
        SYNTAX Integer32
        MAX-ACCESS not-accessible
        STATUS current
        DESCRIPTION
            "Interface Index, equal to ifIndex."
        ::= { hwXQoSIfShapingCfgInfoEntry 1 }

    hwXQoSIfShapingQueueIndex OBJECT-TYPE
        SYNTAX INTEGER
        {
        be(1),
        af1(2),
        af2(3),
        af3(4),
        af4(5),
        ef(6),
        cs6(7),
        cs7(8)        
        }
        MAX-ACCESS not-accessible
        STATUS current
        DESCRIPTION
            "The Shaping queue index 
             be(1),
             af1(2),
             af2(3),
             af3(4),
             af4(5),
             ef(6),
             cs6(7),
             cs7(8)"
        ::= { hwXQoSIfShapingCfgInfoEntry 2 }
                            
    hwXQoSIfShapingQueueCir OBJECT-TYPE
        SYNTAX Integer32       
        MAX-ACCESS read-create
        STATUS current
        DESCRIPTION
            "Committed Information Rate. Unit: kbps."
        ::= { hwXQoSIfShapingCfgInfoEntry 3 }
                                              
    hwXQoSIfShapingQueuePir OBJECT-TYPE
        SYNTAX Integer32       
        MAX-ACCESS read-create
        STATUS current
        DESCRIPTION
            "Peak Information Rate. Unit: kbps.
            Only hardware QoS support this node."
        ::= { hwXQoSIfShapingCfgInfoEntry 4 }
                             
    hwXQoSIfShapingRowStatus OBJECT-TYPE
        SYNTAX RowStatus
        MAX-ACCESS read-create
        STATUS current
        DESCRIPTION
            "RowStatus. Three actions are used: active,
            createAndGo, destroy"
        ::= { hwXQoSIfShapingCfgInfoEntry 5 }            

        
    hwXQoSIfPppoeCfgInfoTable OBJECT-TYPE
        SYNTAX SEQUENCE OF HwXQoSIfPppoeCfgInfoEntry
        MAX-ACCESS not-accessible
        STATUS current
        DESCRIPTION
            "A table of PPPoE configuration information."
        ::= { hwXQoSIfActionObjects 21 }

    
    hwXQoSIfPppoeCfgInfoEntry OBJECT-TYPE
        SYNTAX HwXQoSIfPppoeCfgInfoEntry
        MAX-ACCESS not-accessible
        STATUS current
        DESCRIPTION
            "PPPoE configuration information entry."
        INDEX { hwXQoSIfPppoeIfIndex, hwXQoSIfPppoeMatchType, hwXQoSIfPppoeSourceMac, hwXQoSIfPppoeDestMac }
        ::= { hwXQoSIfPppoeCfgInfoTable 1 }

    
    HwXQoSIfPppoeCfgInfoEntry ::=
        SEQUENCE { 
            hwXQoSIfPppoeIfIndex
                Integer32,
            hwXQoSIfPppoeMatchType
                Integer32,
            hwXQoSIfPppoeSourceMac
                MacAddress,
            hwXQoSIfPppoeDestMac
                MacAddress,
            hwXQoSIfPppoeRowStatus
                RowStatus
         }

    hwXQoSIfPppoeIfIndex OBJECT-TYPE
        SYNTAX Integer32 (1..2147483647)
        MAX-ACCESS not-accessible
        STATUS current
        DESCRIPTION
            "Interface index, equal to ifIndex."
        ::= { hwXQoSIfPppoeCfgInfoEntry 1 }

        
    hwXQoSIfPppoeMatchType OBJECT-TYPE
        SYNTAX Integer32 (1..4)
        MAX-ACCESS not-accessible
        STATUS current
        DESCRIPTION
            "Match type: 1.any 2.source MAC 3.dest MAC 4.source MAC and dest MAC."
        ::= { hwXQoSIfPppoeCfgInfoEntry 2 }

    hwXQoSIfPppoeSourceMac OBJECT-TYPE
        SYNTAX MacAddress
        MAX-ACCESS not-accessible
        STATUS current
        DESCRIPTION
            "Source MAC address."
        ::= { hwXQoSIfPppoeCfgInfoEntry 3 }


    hwXQoSIfPppoeDestMac OBJECT-TYPE
        SYNTAX MacAddress
        MAX-ACCESS not-accessible
        STATUS current
        DESCRIPTION
            "Destination MAC address."
        ::= { hwXQoSIfPppoeCfgInfoEntry 4 }


    hwXQoSIfPppoeRowStatus OBJECT-TYPE
        SYNTAX RowStatus
        MAX-ACCESS read-create
        STATUS current
        DESCRIPTION
            "Row status. Two actions are used: createAndGo, destroy"
        ::= { hwXQoSIfPppoeCfgInfoEntry 5 }

     hwXQoSIfScheduleCfgInfoTable OBJECT-TYPE
        SYNTAX SEQUENCE OF HwXQoSIfScheduleCfgInfoEntry
        MAX-ACCESS not-accessible
        STATUS current
        DESCRIPTION
            "A table of interface schedule configuration information."
        ::= { hwXQoSIfActionObjects 22 }

    hwXQoSIfScheduleCfgInfoEntry OBJECT-TYPE
        SYNTAX HwXQoSIfScheduleCfgInfoEntry
        MAX-ACCESS not-accessible
        STATUS current
        DESCRIPTION
            "Interface schedule configuration information entry."
        INDEX { hwXQoSIfScheduleIfIndex}
        ::= { hwXQoSIfScheduleCfgInfoTable 1 }
    
    HwXQoSIfScheduleCfgInfoEntry ::=
        SEQUENCE { 
            hwXQoSIfScheduleIfIndex
                Integer32, 
            hwXQoSIfScheduleProfile
                OCTET STRING,
            hwXQoSIfScheduleRowStatus
                RowStatus
         }
           
    hwXQoSIfScheduleIfIndex OBJECT-TYPE
        SYNTAX Integer32 (1..2147483647)
        MAX-ACCESS not-accessible
        STATUS current
        DESCRIPTION
            "Interface index, equal to ifIndex."
        ::= { hwXQoSIfScheduleCfgInfoEntry 1 }
                                           
    hwXQoSIfScheduleProfile OBJECT-TYPE
        SYNTAX OCTET STRING (SIZE (1..31))
        MAX-ACCESS read-create
        STATUS current
        DESCRIPTION
            "Name of schedule profile."
        ::= { hwXQoSIfScheduleCfgInfoEntry 2 }

                             
    hwXQoSIfScheduleRowStatus OBJECT-TYPE
        SYNTAX RowStatus
        MAX-ACCESS read-create
        STATUS current
        DESCRIPTION
            "RowStatus. Three actions are used: active,
            createAndGo, destroy"
        ::= { hwXQoSIfScheduleCfgInfoEntry 51 }            
                  
--begin: mod by q00129728 for IPCAR
--  IPCAR Instance on interface Table
 hwXQoSIfIPCarCfgInfoTable OBJECT-TYPE
        SYNTAX SEQUENCE OF HwXQoSIfIPCarCfgInfoEntry
        MAX-ACCESS not-accessible
        STATUS current
        DESCRIPTION
            "A table of IPCAR feature configuration information."
        ::= { hwXQoSIfActionObjects 23 }
 
    hwXQoSIfIPCarCfgInfoEntry OBJECT-TYPE
        SYNTAX HwXQoSIfIPCarCfgInfoEntry
        MAX-ACCESS not-accessible
        STATUS current
        DESCRIPTION
            "IPCAR Configuration Information Entry."
        INDEX { hwXQoSIfIPCarCfgIfIndex, hwXQoSIfIPCarDirection, hwXQoSIPCarRuleIndex }
        ::= { hwXQoSIfIPCarCfgInfoTable 1 }

    HwXQoSIfIPCarCfgInfoEntry ::=
        SEQUENCE { 
            hwXQoSIfIPCarCfgIfIndex
                Integer32,
            hwXQoSIfIPCarDirection
                DirectionType,
            hwXQoSIPCarRuleIndex
                Integer32,                 
            hwXQoSIPCarRuleType
                IPCARRuleType,
            hwXBQoSIPCarIntValue
                Unsigned32,     
            hwXQoSIfIPCarStartIp
                IpAddress,
            hwXQoSIfIPCarEndIp
                IpAddress,    
            hwXQoSIfIPCarCir
                Integer32,
            hwXQoSIfIPCarCbs
                Integer32,
            hwXQoSIfIPCarEbs
                Integer32,
            hwXQoSIfIPCarPir
                Integer32,
            hwXQoSIfIPCarPbs
                Integer32,
            hwXQoSIfIPCarGreenAction
                CarAction,
            hwXQoSIfIPCarGreenRemarkValue
                Integer32,
            hwXQoSIfIPCarYellowAction
                CarAction,
            hwXQoSIfIPCarYellowRemarkValue
                Integer32,
            hwXQoSIfIPCarRedAction
                CarAction,
            hwXQoSIfIPCarRedRemarkValue
                Integer32,                    
            hwXQoSIfIPCarAggregation
                INTEGER,            
            hwXQoSIfIPCarRowStatus
                RowStatus
         } 
         
    hwXQoSIfIPCarCfgIfIndex OBJECT-TYPE
        SYNTAX Integer32
        MAX-ACCESS read-only
        STATUS current
        DESCRIPTION
            "Interface Index, equal to ifIndex.
            This object has no default value."
        ::= { hwXQoSIfIPCarCfgInfoEntry 1 }

    hwXQoSIfIPCarDirection OBJECT-TYPE
        SYNTAX DirectionType
        MAX-ACCESS read-only
        STATUS current
        DESCRIPTION
            "IPCAR Rule direction:
            inbound (1)
            outbound (2)"
        ::= { hwXQoSIfIPCarCfgInfoEntry 2 }
         
    hwXQoSIPCarRuleIndex OBJECT-TYPE
        SYNTAX Integer32
        MAX-ACCESS read-only
        STATUS current
        DESCRIPTION
             "The value of this object identifies the index of IPCAR Rule.
             The value ranges from 0 to 254.
             This object has no default value."
        ::= { hwXQoSIfIPCarCfgInfoEntry 3 }
    
    hwXQoSIPCarRuleType OBJECT-TYPE
            SYNTAX IPCARRuleType
            MAX-ACCESS read-create
            STATUS current
            DESCRIPTION
                "The value of this object identifies the rule type.
                The value of this object can be any of the following: 
                ipv4-acl(1)
                ipv4-SrcIp(2)
                ipv4-DstIp(3)
                This object has no default value." 
        ::= { hwXQoSIfIPCarCfgInfoEntry 4 } 
        
    hwXBQoSIPCarIntValue OBJECT-TYPE
            SYNTAX Unsigned32
            MAX-ACCESS read-create
            STATUS current
            DESCRIPTION
                "This object indicates the rule contents. The value range and the default value of the object vary with hwXQoSIPCarRuleType.
                 When the supported type is ipv4-acl(2), the value of this object ranges from 2000 to 4999.
                 This object has no default value."
            ::= { hwXQoSIfIPCarCfgInfoEntry 5 }  
            
    hwXQoSIfIPCarStartIp OBJECT-TYPE
        SYNTAX IpAddress
        MAX-ACCESS read-create
        STATUS current
        DESCRIPTION
            "The object indicates the start of source IP address segment.
            This object has no default value.
            0.0.0.0 is invalid value."
         ::= { hwXQoSIfIPCarCfgInfoEntry 6 } 

    hwXQoSIfIPCarEndIp OBJECT-TYPE
        SYNTAX IpAddress
        MAX-ACCESS read-create
        STATUS current
        DESCRIPTION
            "The object indicates the end of source IP address segment.
            This object has no default value.
            0.0.0.0 is invalid value."
         ::= { hwXQoSIfIPCarCfgInfoEntry 7 }

    hwXQoSIfIPCarCir OBJECT-TYPE
        SYNTAX Integer32
        MAX-ACCESS read-create
        STATUS current
        DESCRIPTION
            "Committed Information Rate. Unit: kbps.
            The value ranges from 8 to 4294967295, with no default value."
        ::= { hwXQoSIfIPCarCfgInfoEntry 8 }

    
    hwXQoSIfIPCarCbs OBJECT-TYPE
        SYNTAX Integer32
        MAX-ACCESS read-create
        STATUS current
        DESCRIPTION
            "Committed Burst Size. Unit: byte
            The value ranges from 1500 to 4294967295 bytes."
        ::= { hwXQoSIfIPCarCfgInfoEntry 9 }

    
    hwXQoSIfIPCarEbs OBJECT-TYPE
        SYNTAX Integer32
        MAX-ACCESS read-create
        STATUS current
        DESCRIPTION
            "Excess Burst Size. Unit: byte.
            Only software QoS support this node.
            -1 is returned only when getting value from hardware QoS.
            -1 can't be set."
        DEFVAL { 0 }
        ::= { hwXQoSIfIPCarCfgInfoEntry 10 }

    
    hwXQoSIfIPCarPir OBJECT-TYPE
        SYNTAX Integer32
        MAX-ACCESS read-create
        STATUS current
        DESCRIPTION
            "Peak Information Rate. Unit: kbps.
            The value ranges from 8 to 4294967295"
        ::= { hwXQoSIfIPCarCfgInfoEntry 11 }

    
    hwXQoSIfIPCarPbs OBJECT-TYPE
        SYNTAX Integer32
        MAX-ACCESS read-create
        STATUS current
        DESCRIPTION
            "Peak Burst Size. Unit: byte.
            The value ranges from 1500 to 4294967295 bytes."
        ::= { hwXQoSIfIPCarCfgInfoEntry 12 }

    
    hwXQoSIfIPCarGreenAction OBJECT-TYPE
        SYNTAX CarAction
        MAX-ACCESS read-create
        STATUS current
        DESCRIPTION
            "The value of this object identifies the action adopted when CIR is not reached.
                 pass (1),
                 discard (2),
                 remark IP Precedence (3),
                 remark DSCP(4),
                 remark Mpls Exp(5),
                 remark (6),
                 remark 8021p(7)
                 The default value is pass (1).
                 "
        DEFVAL { pass }
        ::= { hwXQoSIfIPCarCfgInfoEntry 13 }

    
    hwXQoSIfIPCarGreenRemarkValue OBJECT-TYPE
        SYNTAX Integer32 (-1 | 0..63)
        MAX-ACCESS read-create
        STATUS current
        DESCRIPTION
            "The value is to remark When green action is remarking.
            For remarking DSCP, the range is 0~63;
            For remarking IP Precedence and MPLS EXP, the range is 0~7;
            Only software QoS support this node.
            -1 is returned only when getting value from hardware QoS or when action being pass,discard of software QoS.
            -1 can't be set."
        ::= { hwXQoSIfIPCarCfgInfoEntry 14 }

    
    hwXQoSIfIPCarYellowAction OBJECT-TYPE
        SYNTAX CarAction
        MAX-ACCESS read-create
        STATUS current
        DESCRIPTION
            "The value of this object identifies the action adopted when CIR is exceeded but PIR is not reached.
                 pass (1),
                 discard (2),
                 remark IP Precedence (3),
                 remark DSCP(4),
                 remark Mpls Exp(5),
                 remark (6),
                 remark 8021p(7)
                 The default value is pass (1).
                 " 
        DEFVAL { pass }
        ::= { hwXQoSIfIPCarCfgInfoEntry 15 }

    hwXQoSIfIPCarYellowRemarkValue OBJECT-TYPE
        SYNTAX Integer32 (-1 | 0..63)
        MAX-ACCESS read-create
        STATUS current
        DESCRIPTION
            "The value is to remark When yellow action is remarking.
            For remarking DSCP, the range is 0~63;
            For remarking IP Precedence and MPLS EXP, the range is 0~7;
            Only software QoS support this node.
            -1 is returned only when getting value from hardware QoS or when action being pass,discard of software QoS.
            -1 can't be set."
        ::= { hwXQoSIfIPCarCfgInfoEntry 16 }
    
    hwXQoSIfIPCarRedAction OBJECT-TYPE
        SYNTAX CarAction
        MAX-ACCESS read-create
        STATUS current
        DESCRIPTION
            "The value of this object identifies the action adopted when CIR is exceeded but PIR is not reached.
                 pass (1),
                 discard (2),
                 remark IP Precedence (3),
                 remark DSCP(4),
                 remark Mpls Exp(5),
                 remark (6),
                 remark 8021p(7)
                 The default value is pass (1).
                 "
        DEFVAL { discard }
        ::= { hwXQoSIfIPCarCfgInfoEntry 17 }
  
    hwXQoSIfIPCarRedRemarkValue OBJECT-TYPE
        SYNTAX Integer32 (-1 | 0..63)
        MAX-ACCESS read-create
        STATUS current
        DESCRIPTION
            "The value is to remark When red action is remarking.
            For remarking DSCP, the range is 0~63;
            For remarking IP Precedence and MPLS EXP, the range is 0~7;
            Only software QoS support this node.
            -1 is returned only when getting value from hardware QoS or when action being pass,discard of software QoS.
            -1 can't be set."
        ::= { hwXQoSIfIPCarCfgInfoEntry 18 }
                                                                                                        
     hwXQoSIfIPCarAggregation OBJECT-TYPE
         SYNTAX INTEGER 
         {
            aggregationCar(1),
            noneAggregationCar(2)
         }
         MAX-ACCESS read-create
         STATUS current
         DESCRIPTION
            "aggregationCar(1): aggregation car;
            noneAggregationCar(2) : none aggregation car."
          ::= { hwXQoSIfIPCarCfgInfoEntry 19 }    
            
    hwXQoSIfIPCarRowStatus OBJECT-TYPE
        SYNTAX RowStatus
        MAX-ACCESS read-create
        STATUS current
        DESCRIPTION
            "RowStatus. Three actions are used: active,
            createAndGo, destroy"
        ::= { hwXQoSIfIPCarCfgInfoEntry 20 }        
--end: mod by q00129728 for IPCAR  

-- 8021P CAR		
    hwXQoSIf8021PCarCfgInfoTable OBJECT-TYPE
	SYNTAX SEQUENCE OF HwXQoSIf8021PCarCfgInfoEntry
	MAX-ACCESS not-accessible
	STATUS current
	DESCRIPTION
		"A table of 8021P CAR feature configuration information."
	::= { hwXQoSIfActionObjects 24 }

		
    hwXQoSIf8021PCarCfgInfoEntry OBJECT-TYPE
	SYNTAX HwXQoSIf8021PCarCfgInfoEntry
	MAX-ACCESS not-accessible
	STATUS current
	DESCRIPTION
		"8021P CAR Configuration Information Entry."
	INDEX { hwXQoSIf8021PCarIfIndex, hwXQoSIf8021PCarDirection, hwXQoSIf8021PCarIndexId }
	::= { hwXQoSIf8021PCarCfgInfoTable 1 }

		
    HwXQoSIf8021PCarCfgInfoEntry ::=
	SEQUENCE { 
		hwXQoSIf8021PCarIfIndex
			Integer32,
		hwXQoSIf8021PCarDirection
			INTEGER,
		hwXQoSIf8021PCarIndexId
			Integer32,
		hwXQoSIf8021PCarCir
			Unsigned32,
		hwXQoSIf8021PCarCbs
			Unsigned32,
		hwXQoSIf8021PCarPir
			Unsigned32,
		hwXQoSIf8021PCarPbs
			Unsigned32,
		hwXQoSIf8021PCar8021pValue
			OCTET STRING,
		hwXQoSIf8021PCarRowStatus
			RowStatus
	 }
			
    hwXQoSIf8021PCarIfIndex OBJECT-TYPE
	SYNTAX Integer32
	MAX-ACCESS read-only
	STATUS current
	DESCRIPTION
		"Interface Index, equal to ifIndex."
	::= { hwXQoSIf8021PCarCfgInfoEntry 1 }

		
    hwXQoSIf8021PCarDirection OBJECT-TYPE
	SYNTAX INTEGER
		{
		inbound(1),
		outbound(2)
		}
	MAX-ACCESS read-only
	STATUS current
	DESCRIPTION
		"Apply direction:inbound (1),outbound (2)."
	::= { hwXQoSIf8021PCarCfgInfoEntry 2 }

		
    hwXQoSIf8021PCarIndexId OBJECT-TYPE
	SYNTAX Integer32 (0..7)
	MAX-ACCESS read-only
	STATUS current
	DESCRIPTION
		"Every Command Index ID."
	::= { hwXQoSIf8021PCarCfgInfoEntry 3 }

		
    hwXQoSIf8021PCarCir OBJECT-TYPE
	SYNTAX Unsigned32 (64..4294967295)
	MAX-ACCESS read-create
	STATUS current
	DESCRIPTION
		"Committed Information Rate. Unit: kbps.
     		 Unsigned32<64-4294967295> "
	::= { hwXQoSIf8021PCarCfgInfoEntry 4 }


    hwXQoSIf8021PCarCbs OBJECT-TYPE
	SYNTAX Unsigned32 (1500..4294967295)
	MAX-ACCESS read-create
	STATUS current
	DESCRIPTION
		"Committed Burst Size. Unit: byte
     		 Unsigned32<1500-4294967295> "
	::= { hwXQoSIf8021PCarCfgInfoEntry 5 }

		
    hwXQoSIf8021PCarPir OBJECT-TYPE
	SYNTAX Unsigned32 (64..4294967295)
	MAX-ACCESS read-create
	STATUS current
	DESCRIPTION
		"Peak Information Rate. Unit: kbps.
		 Unsigned32<64-4294967295> "
	::= { hwXQoSIf8021PCarCfgInfoEntry 6 }

		
    hwXQoSIf8021PCarPbs OBJECT-TYPE
	SYNTAX Unsigned32 (1500..4294967295)
	MAX-ACCESS read-create
	STATUS current
	DESCRIPTION
		"Peak Burst Size. Unit: byte.
 	         Unsigned32<1500-4294967295> "
	::= { hwXQoSIf8021PCarCfgInfoEntry 7 }

		
    hwXQoSIf8021PCar8021pValue OBJECT-TYPE
	SYNTAX OCTET STRING (SIZE (0..31))
	MAX-ACCESS read-create
	STATUS current
	DESCRIPTION
		"VLAN 802.1p value.
		 STRING<0-7> "
	::= { hwXQoSIf8021PCarCfgInfoEntry 8 }

		
    hwXQoSIf8021PCarRowStatus OBJECT-TYPE
	SYNTAX RowStatus
	MAX-ACCESS read-create
	STATUS current
	DESCRIPTION
		"RowStatus. Three actions are used: active(1),
	     	 createAndGo(4), destroy(6)."
	::= { hwXQoSIf8021PCarCfgInfoEntry 9 }
                  
--   Cpcar command 
    hwXQoSCpcarObjects OBJECT IDENTIFIER ::= { hwXQoSObjects 3 }

    
--    Cp car
    hwXQoSCpcarCfgInfoTable OBJECT-TYPE
        SYNTAX SEQUENCE OF HwXQoSCpcarCfgInfoEntry
        MAX-ACCESS not-accessible
        STATUS current
        DESCRIPTION
            "A table of cp car configuration information."
        ::= { hwXQoSCpcarObjects 1 }

    
    hwXQoSCpcarCfgInfoEntry OBJECT-TYPE
        SYNTAX HwXQoSCpcarCfgInfoEntry
        MAX-ACCESS not-accessible
        STATUS current
        DESCRIPTION
            "Diff-server domain Information Entry."
        INDEX { hwXQoSCpcarIndex }
        ::= { hwXQoSCpcarCfgInfoTable 1 }

    
    HwXQoSCpcarCfgInfoEntry ::=
        SEQUENCE { 
            hwXQoSCpcarIndex
                Integer32,
            hwXQoSCpcarName
                OCTET STRING,
            hwXQoSCpcarRowStatus
                RowStatus
         }

    hwXQoSCpcarIndex OBJECT-TYPE
        SYNTAX Integer32
        MAX-ACCESS read-only
        STATUS current
        DESCRIPTION
            "Index of cp car domain."
        ::= { hwXQoSCpcarCfgInfoEntry 1 }

    
    hwXQoSCpcarName OBJECT-TYPE
        SYNTAX OCTET STRING (SIZE (1..31))
        MAX-ACCESS read-create
        STATUS current
        DESCRIPTION
            "Exception name of cp car."
        ::= { hwXQoSCpcarCfgInfoEntry 2 }

    
    hwXQoSCpcarRowStatus OBJECT-TYPE
        SYNTAX RowStatus
        MAX-ACCESS read-create
        STATUS current
        DESCRIPTION
            "RowStatus. Three actions are used: active,
            createAndGo, destroy"
        ::= { hwXQoSCpcarCfgInfoEntry 3 }

    
--    filter in cp car        
    hwXQoSCpCarFilterCfgInfoTable OBJECT-TYPE
        SYNTAX SEQUENCE OF HwXQoSCpCarFilterCfgInfoEntry
        MAX-ACCESS not-accessible
        STATUS current
        DESCRIPTION
            "A table of cpcar filter configuration information."
        ::= { hwXQoSCpcarObjects 2 }

    
    hwXQoSCpCarFilterCfgInfoEntry OBJECT-TYPE
        SYNTAX HwXQoSCpCarFilterCfgInfoEntry
        MAX-ACCESS not-accessible
        STATUS current
        DESCRIPTION
            "Diff-serve domain 8021p phb Configuration Information Entry."
        INDEX { hwXQoSCpcarIndex }
        ::= { hwXQoSCpCarFilterCfgInfoTable 1 }

    
    HwXQoSCpCarFilterCfgInfoEntry ::=
        SEQUENCE { 
            hwXQoSCpCarFilterAction
                INTEGER,
            hwXQoSCpCarFilterRowStatus
                RowStatus
         }

    hwXQoSCpCarFilterAction OBJECT-TYPE
        SYNTAX INTEGER
        {
            pass(1),
            drop(2)
        }
        MAX-ACCESS read-only
        STATUS current
        DESCRIPTION
            "filter action
            1:pass
            2:drop
            DEFVAL { pass }"        
        ::= { hwXQoSCpCarFilterCfgInfoEntry 1 }

    
    hwXQoSCpCarFilterRowStatus OBJECT-TYPE
        SYNTAX RowStatus
        MAX-ACCESS read-create
        STATUS current
        DESCRIPTION
            "RowStatus. Three actions are used: active,
            createAndGo, destroy"
        ::= { hwXQoSCpCarFilterCfgInfoEntry 2 }

    
--    CAR in cp car
    hwXQoSCpCarCfgInfoTable OBJECT-TYPE
        SYNTAX SEQUENCE OF HwXQoSCpCarCfgInfoEntry
        MAX-ACCESS not-accessible
        STATUS current
        DESCRIPTION
            "A table of CAR feature configuration information."
        ::= { hwXQoSCpcarObjects 3 }

    
    hwXQoSCpCarCfgInfoEntry OBJECT-TYPE
        SYNTAX HwXQoSCpCarCfgInfoEntry
        MAX-ACCESS not-accessible
        STATUS current
        DESCRIPTION
            "CAR Configuration Information Entry."
        INDEX { hwXQoSCpcarIndex }
        ::= { hwXQoSCpCarCfgInfoTable 1 }

    
    HwXQoSCpCarCfgInfoEntry ::=
        SEQUENCE { 
            hwXQoSCpCarSlotId
                Integer32,
            hwXQoSCpCarCir
                Integer32,
            hwXQoSCpCarCbs
                Integer32,
            hwXQoSCpCarEbs
                Integer32,
            hwXQoSCpCarPir
                Integer32,
            hwXQoSCpCarPbs
                Integer32,
            hwXQoSCpCarGreenAction
                CarAction,
            hwXQoSCpCarGreenRemarkValue
                Integer32,
            hwXQoSCpCarYellowAction
                CarAction,
            hwXQoSCpCarYellowRemarkValue
                Integer32,
            hwXQoSCpCarRedAction
                CarAction,
            hwXQoSCpCarRedRemarkValue
                Integer32,
            hwXQoSCpCarRowStatus
                RowStatus
         }

    hwXQoSCpCarSlotId OBJECT-TYPE
        SYNTAX Integer32 (1..16)
        MAX-ACCESS read-create
        STATUS current
        DESCRIPTION
            "Target slot"
        ::= { hwXQoSCpCarCfgInfoEntry 1 }

    hwXQoSCpCarCir OBJECT-TYPE
        SYNTAX Integer32 (8..10000000)
        MAX-ACCESS read-create
        STATUS current
        DESCRIPTION
            "Committed Information Rate. Unit: kbps.
            software QoS: 8..155000
            hardware QoS: 100..10000000"
        ::= { hwXQoSCpCarCfgInfoEntry 2 }

    
    hwXQoSCpCarCbs OBJECT-TYPE
        SYNTAX Integer32 (64..19375000)
        MAX-ACCESS read-create
        STATUS current
        DESCRIPTION
            "Committed Burst Size. Unit: byte
            software QoS: 1875..19375000 (default:max(cir*125/2,1875))
            hardware QoS: 64..131071(default:12288)"
        ::= { hwXQoSCpCarCfgInfoEntry 3 }

    
    hwXQoSCpCarEbs OBJECT-TYPE
        SYNTAX Integer32 (-1 | 0..19375000)
        MAX-ACCESS read-create
        STATUS current
        DESCRIPTION
            "Excess Burst Size. Unit: byte. 0..19375000
            Only software QoS support this node.
            -1 is returned only when getting value from hardware QoS.
            -1 can't be set."
        DEFVAL { 0 }
        ::= { hwXQoSCpCarCfgInfoEntry 4 }

    
    hwXQoSCpCarPir OBJECT-TYPE
        SYNTAX Integer32 (-1 | 0 | 100..10000000)
        MAX-ACCESS read-create
        STATUS current
        DESCRIPTION
            "Peak Information Rate. Unit: kbps. 100..10000000
            Only hardware QoS support this node.
            -1 is returned only when getting value from software QoS.
            -1 can't be set.
            0 is the default value"
        ::= { hwXQoSCpCarCfgInfoEntry 5 }

    
    hwXQoSCpCarPbs OBJECT-TYPE
        SYNTAX Integer32 (-1 | 0 | 64..4000000)
        MAX-ACCESS read-create
        STATUS current
        DESCRIPTION
            "Peak Burst Size. Unit: byte.
            64..4000000.(default:cbs when Peak Information Rate configured)
            Only hardware QoS support this node.
            -1 is returned only when getting value from software QoS.
            -1 can't be set.
            0 is the default value"
        ::= { hwXQoSCpCarCfgInfoEntry 6 }

    
    hwXQoSCpCarGreenAction OBJECT-TYPE
        SYNTAX CarAction
        MAX-ACCESS read-create
        STATUS current
        DESCRIPTION
            "Green Action:
            pass (1)
            discard (2)                
            remark IP Precedence (3)
            remark DSCP (4)                            
            remark MPLS EXP (5)
            remark (6)
            Hardware QoS : pass,discard,remark.
            Software QoS : pass,discard,remark IP Precedence,remark DSCP,remark MPLS EXP.
            "
        DEFVAL { pass }
        ::= { hwXQoSCpCarCfgInfoEntry 7 }

    
    hwXQoSCpCarGreenRemarkValue OBJECT-TYPE
        SYNTAX Integer32 (-1 | 0..63)
        MAX-ACCESS read-create
        STATUS current
        DESCRIPTION
            "The value is to remark When green action is remarking.
            For remarking DSCP, the range is 0~63;
            For remarking IP Precedence and MPLS EXP, the range is 0~7;
            Only software QoS support this node.
            -1 is returned only when getting value from hardware QoS or when action being pass,discard of software QoS.
            -1 can't be set."
        ::= { hwXQoSCpCarCfgInfoEntry 8 }

    
    hwXQoSCpCarYellowAction OBJECT-TYPE
        SYNTAX CarAction
        MAX-ACCESS read-create
        STATUS current
        DESCRIPTION
            "Yellow Action:
            unavailable(-1)
            pass (1)
            discard (2)
            remark IP Precedence (3)
            remark DSCP (4)
            remark MPLS EXP (5)
            remark(6)
            Only hardware QoS support this node.Hardware QoS support pass,discard,remark.
            -1 is returned only when getting value from software QoS.
            -1 can't be set."
        ::= { hwXQoSCpCarCfgInfoEntry 9 }

    
    hwXQoSCpCarYellowRemarkValue OBJECT-TYPE
        SYNTAX Integer32 (-1 | 0..63)
        MAX-ACCESS read-create
        STATUS current
        DESCRIPTION
            "The value is to remark When yellow action is remarking.
            For remarking DSCP, the range is 0~63;
            For remarking IP Precedence and MPLS EXP, the range is 0~7;
            Only software QoS support this node.
            -1 is returned only when getting value from hardware QoS or when action being pass,discard of software QoS.
            -1 can't be set."
        ::= { hwXQoSCpCarCfgInfoEntry 10 }

    
    hwXQoSCpCarRedAction OBJECT-TYPE
        SYNTAX CarAction
        MAX-ACCESS read-create
        STATUS current
        DESCRIPTION
            "Red Action:
            pass (1)
            discard (2)                
            remark IP Precedence (3)
            remark DSCP (4)
            remark MPLS EXP (5)
            remark (6)
            Hardware QoS : pass,discard,remark.
            Software QoS : pass,discard,remark IP Precedence,remark DSCP,remark MPLS EXP.
            "
        DEFVAL { discard }
        ::= { hwXQoSCpCarCfgInfoEntry 11 }

    
    hwXQoSCpCarRedRemarkValue OBJECT-TYPE
        SYNTAX Integer32 (-1 | 0..63)
        MAX-ACCESS read-create
        STATUS current
        DESCRIPTION
            "The value is to remark When red action is remarking.
            For remarking DSCP, the range is 0~63;
            For remarking IP Precedence and MPLS EXP, the range is 0~7;
            Only software QoS support this node.
            -1 is returned only when getting value from hardware QoS or when action being pass,discard of software QoS.
            -1 can't be set."
        ::= { hwXQoSCpCarCfgInfoEntry 12 }

    
    hwXQoSCpCarRowStatus OBJECT-TYPE
        SYNTAX RowStatus
        MAX-ACCESS read-create
        STATUS current
        DESCRIPTION
            "RowStatus. Three actions are used: active,
            createAndGo, destroy"
        ::= { hwXQoSCpCarCfgInfoEntry 13 }

    
--    Policy Instance in cp car            
    hwXQoSCpApplyPolicyTable OBJECT-TYPE
        SYNTAX SEQUENCE OF HwXQoSCpApplyPolicyEntry
        MAX-ACCESS not-accessible
        STATUS current
        DESCRIPTION
            "A table of QoS policy instance."
        ::= { hwXQoSCpcarObjects 4 }

    
    hwXQoSCpApplyPolicyEntry OBJECT-TYPE
        SYNTAX HwXQoSCpApplyPolicyEntry
        MAX-ACCESS not-accessible
        STATUS current
        DESCRIPTION
            "Policy applied on Ethernet Vlan Configuration Information Entry."
        INDEX { hwXQoSCpcarIndex }
        ::= { hwXQoSCpApplyPolicyTable 1 }

    
    HwXQoSCpApplyPolicyEntry ::=
        SEQUENCE { 
            hwXQoSCpApplyPolicyName
                OCTET STRING,
            hwXQoSCpApplyPolicyRowStatus
                RowStatus
         }

    hwXQoSCpApplyPolicyName OBJECT-TYPE
        SYNTAX OCTET STRING (SIZE (1..31))
        MAX-ACCESS read-create
        STATUS current
        DESCRIPTION
            "Name of Traffic Policy."
        ::= { hwXQoSCpApplyPolicyEntry 1 }

    
    hwXQoSCpApplyPolicyRowStatus OBJECT-TYPE
        SYNTAX RowStatus
        MAX-ACCESS read-create
        STATUS current
        DESCRIPTION
            "RowStatus. Three actions are used: active,
            createAndGo, destroy"
        ::= { hwXQoSCpApplyPolicyEntry 2 }

    -- 1.3.6.1.4.1.2011.5.25.32.4.1.3.5
    hwXQoSCpCarActionTable OBJECT-TYPE
        SYNTAX SEQUENCE OF HwXQoSCpCarActionEntry
        MAX-ACCESS not-accessible
        STATUS current
        DESCRIPTION
            "A table of cp car action configuration information."
        ::= { hwXQoSCpcarObjects 5 }
    
    -- 1.3.6.1.4.1.2011.5.25.32.4.1.3.5.1
    hwXQoSCpCarActionEntry OBJECT-TYPE
        SYNTAX HwXQoSCpCarActionEntry
        MAX-ACCESS not-accessible
        STATUS current
        DESCRIPTION
            "Cp car action configuration information entry."
        INDEX { hwXQoSCpCarActionSlotIndex, hwXQoSCpCarActionPacketType }
        ::= { hwXQoSCpCarActionTable 1 }
    
    HwXQoSCpCarActionEntry ::=
        SEQUENCE { 
            hwXQoSCpCarActionSlotIndex
                Integer32,
            hwXQoSCpCarActionPacketType
                    Integer32,
            hwXQoSCpCarActionPacketTypeName
                OCTET STRING,
            hwXQoSCpCarActionType
                BITS,
            hwXQoSCpCarActionPolicyName
                OCTET STRING,
            hwXQoSCpCarActionCarCir
                Integer32,
            hwXQoSCpCarActionCarCbs
                Integer32,
            hwXQoSCpCarActionCarEbs
                Integer32,
            hwXQoSCpCarActionCarPir
                Integer32,
            hwXQoSCpCarActionCarPbs
                Integer32,
            hwXQoSCpCarActionGreenAction
                CarAction,
            hwXQoSCpCarActionGreenRemarkValue
                Integer32,
            hwXQoSCpCarActionYellowAction
                CarAction,
            hwXQoSCpCarActionYellowRemarkValue
                Integer32,
            hwXQoSCpCarActionRedAction
                CarAction,
            hwXQoSCpCarActionRedRemarkValue
                Integer32,
            hwXQoSCpCarActionSetDefault
                Integer32
         }

    -- 1.3.6.1.4.1.2011.5.25.32.4.1.3.5.1.1
    hwXQoSCpCarActionSlotIndex OBJECT-TYPE
        SYNTAX Integer32
        MAX-ACCESS not-accessible
        STATUS current
        DESCRIPTION
            "Slot index."
        ::= { hwXQoSCpCarActionEntry 1 }
    
    -- 1.3.6.1.4.1.2011.5.25.32.4.1.3.5.1.2
    hwXQoSCpCarActionPacketType OBJECT-TYPE
        SYNTAX Integer32
        MAX-ACCESS not-accessible
        STATUS current
        DESCRIPTION
            "Packet type."
        ::= { hwXQoSCpCarActionEntry 2 }
    
    -- 1.3.6.1.4.1.2011.5.25.32.4.1.3.5.1.3
    hwXQoSCpCarActionPacketTypeName OBJECT-TYPE
        SYNTAX OCTET STRING (SIZE (1..31))
        MAX-ACCESS read-only
        STATUS current
        DESCRIPTION
            "Name of packet type."
        ::= { hwXQoSCpCarActionEntry 3 }
        
    -- 1.3.6.1.4.1.2011.5.25.32.4.1.3.5.1.4
    hwXQoSCpCarActionType OBJECT-TYPE
        SYNTAX BITS
            {
            pass(0),
            discard(1),
            car(2),
            trafficPolicy(3)
            }
        MAX-ACCESS read-write
        STATUS current
        DESCRIPTION
            "Action type."
        ::= { hwXQoSCpCarActionEntry 4 }
    
        -- 1.3.6.1.4.1.2011.5.25.32.4.1.3.5.1.5
    hwXQoSCpCarActionPolicyName OBJECT-TYPE
        SYNTAX OCTET STRING (SIZE (0..31))
        MAX-ACCESS read-write
        STATUS current
        DESCRIPTION
            "Policy Name"
        DEFVAL { "" }
        ::= { hwXQoSCpCarActionEntry 5 }
    
     -- 1.3.6.1.4.1.2011.5.25.32.4.1.3.5.1.6
    hwXQoSCpCarActionCarCir OBJECT-TYPE
        SYNTAX Integer32
        MAX-ACCESS read-write
        STATUS current
        DESCRIPTION
            "Committed Information Rate. Unit: kbps."
        DEFVAL { -1 }
        ::= { hwXQoSCpCarActionEntry 6 }
    
    -- 1.3.6.1.4.1.2011.5.25.32.4.1.3.5.1.7
    hwXQoSCpCarActionCarCbs OBJECT-TYPE
        SYNTAX Integer32
        MAX-ACCESS read-write
        STATUS current
        DESCRIPTION
            "Committed Burst Size. Unit: byte"
        DEFVAL { -1 }
        ::= { hwXQoSCpCarActionEntry 7 }
        
        hwXQoSCpCarActionCarEbs OBJECT-TYPE
        SYNTAX Integer32
        MAX-ACCESS read-write
        STATUS current
        DESCRIPTION
            "Excess Burst Size. Unit: byte."
        DEFVAL { -1}
        ::= { hwXQoSCpCarActionEntry 8 }
    
    -- 1.3.6.1.4.1.2011.5.25.32.4.1.3.5.1.9
    hwXQoSCpCarActionCarPir OBJECT-TYPE
        SYNTAX Integer32
        MAX-ACCESS read-write
        STATUS current
        DESCRIPTION
            "Peak Information Rate. Unit: kbps."
        DEFVAL { -1 }
        ::= { hwXQoSCpCarActionEntry 9 }
    
    -- 1.3.6.1.4.1.2011.5.25.32.4.1.3.5.1.10
    hwXQoSCpCarActionCarPbs OBJECT-TYPE
        SYNTAX Integer32
        MAX-ACCESS read-write
        STATUS current
        DESCRIPTION
            "Peak Burst Size. Unit: byte."
        DEFVAL { -1 }
        ::= { hwXQoSCpCarActionEntry 10 }
    
    -- 1.3.6.1.4.1.2011.5.25.32.4.1.3.5.1.11
    hwXQoSCpCarActionGreenAction OBJECT-TYPE
        SYNTAX CarAction
        MAX-ACCESS read-write
        STATUS current
        DESCRIPTION
            "Green Action.
            pass (1)
            discard (2)                
            remark IP Precedence (3)
            remark DSCP (4)                            
            remark MPLS EXP (5)
            remark (6)
            Hardware QoS : pass,discard,remark.
            Software QoS : pass,discard,remark IP Precedence,remark DSCP,remark MPLS EXP."
        ::= { hwXQoSCpCarActionEntry 11 }
    
    -- 1.3.6.1.4.1.2011.5.25.32.4.1.3.5.1.12
    hwXQoSCpCarActionGreenRemarkValue OBJECT-TYPE
        SYNTAX Integer32 (-1 | 0..63)
        MAX-ACCESS read-write
        STATUS current
        DESCRIPTION
            "The value is to remark When green action is remarking.
            For remarking DSCP, the range is 0~63;
            For remarking IP Precedence and MPLS EXP, the range is 0~7;
            Only software QoS support this node.
            -1 is returned only when getting value from hardware QoS or when action being pass,discard of software QoS.
            -1 can't be set."
        ::= { hwXQoSCpCarActionEntry 12 }
        
    -- 1.3.6.1.4.1.2011.5.25.32.4.1.3.5.1.13
    hwXQoSCpCarActionYellowAction OBJECT-TYPE
        SYNTAX CarAction
        MAX-ACCESS read-write
        STATUS current
        DESCRIPTION
            "Yellow Action.
            pass (1)
            discard (2)                
            remark IP Precedence (3)
            remark DSCP (4)                            
            remark MPLS EXP (5)
            remark (6)
            Hardware QoS : pass,discard,remark.
            Software QoS : pass,discard,remark IP Precedence,remark DSCP,remark MPLS EXP."
        ::= { hwXQoSCpCarActionEntry 13 }
    
    -- 1.3.6.1.4.1.2011.5.25.32.4.1.3.5.1.14
    hwXQoSCpCarActionYellowRemarkValue OBJECT-TYPE
        SYNTAX Integer32 (-1 | 0..63)
        MAX-ACCESS read-write
        STATUS current
        DESCRIPTION
            "The value is to remark When yellow action is remarking.
            For remarking DSCP, the range is 0~63;
            For remarking IP Precedence and MPLS EXP, the range is 0~7;
            Only software QoS support this node.
            -1 is returned only when getting value from hardware QoS or when action being pass,discard of software QoS.
            -1 can't be set."
        ::= { hwXQoSCpCarActionEntry 14 }
        
    -- 1.3.6.1.4.1.2011.5.25.32.4.1.3.5.1.15
    hwXQoSCpCarActionRedAction OBJECT-TYPE
        SYNTAX CarAction
        MAX-ACCESS read-write
        STATUS current
        DESCRIPTION
            "Red Action.
            pass (1)
            discard (2)                
            remark IP Precedence (3)
            remark DSCP (4)                            
            remark MPLS EXP (5)
            remark (6)
            Hardware QoS : pass,discard,remark.
            Software QoS : pass,discard,remark IP Precedence,remark DSCP,remark MPLS EXP."
        ::= { hwXQoSCpCarActionEntry 15 }
        
    -- 1.3.6.1.4.1.2011.5.25.32.4.1.3.5.1.16
    hwXQoSCpCarActionRedRemarkValue OBJECT-TYPE
        SYNTAX Integer32 (-1 | 0..63)
        MAX-ACCESS read-write
        STATUS current
        DESCRIPTION
            "The value is to remark When red action is remarking.
            For remarking DSCP, the range is 0~63;
            For remarking IP Precedence and MPLS EXP, the range is 0~7;
            Only software QoS support this node.
            -1 is returned only when getting value from hardware QoS or when action being pass,discard of software QoS.
            -1 can't be set."
        ::= { hwXQoSCpCarActionEntry 16 }
        
    -- 1.3.6.1.4.1.2011.5.25.32.4.1.3.5.1.17
    hwXQoSCpCarActionSetDefault OBJECT-TYPE
        SYNTAX Integer32 (0..1)
        MAX-ACCESS read-write
        STATUS current
        DESCRIPTION
            "This OID is used for setting the CP CAR info to default.
            When you want to set the value to default, set this OID to 1."
        ::= { hwXQoSCpCarActionEntry 17 }
        
    -- 1.3.6.1.4.1.2011.5.25.32.4.1.4
    hwXQoSStatisticsObjects OBJECT IDENTIFIER ::= { hwXQoSObjects 4 }
    
--    Cp car statistics information 
    hwXQoSCpcarStaticsObjects OBJECT IDENTIFIER ::= { hwXQoSStatisticsObjects 2 }

    
--    Cp car statistics            
    hwXQoSCpcarRunInfoTable OBJECT-TYPE
        SYNTAX SEQUENCE OF HwXQoSCpcarRunInfoEntry
        MAX-ACCESS not-accessible
        STATUS current
        DESCRIPTION
            "A table of Running statistics for sample
            in a QoS policy applied on the interface."
        ::= { hwXQoSCpcarStaticsObjects 1 }

    
    hwXQoSCpcarRunInfoEntry OBJECT-TYPE
        SYNTAX HwXQoSCpcarRunInfoEntry
        MAX-ACCESS not-accessible
        STATUS current
        DESCRIPTION
            "Cp car statistics entry."
        INDEX { hwXQoSCpcarIndex }
        ::= { hwXQoSCpcarRunInfoTable 1 }

    
    HwXQoSCpcarRunInfoEntry ::=
        SEQUENCE { 
            hwXQoSCpcarPassedPackets
                Counter64,
            hwXQoSCpcarPassededBytes
                Counter64,
            hwXQoSCpcarTotalPackets
                Counter64,
            hwXQoSCpcarTotalBytes
                Counter64,
            hwXQoSCpcarDiscardedPackets
                Counter64,
            hwXQoSCpcarDiscardedBytes
                Counter64
         }

    hwXQoSCpcarPassedPackets OBJECT-TYPE
        SYNTAX Counter64
        MAX-ACCESS read-only
        STATUS current
        DESCRIPTION
            "Number of packets passed of enqueue."
        ::= { hwXQoSCpcarRunInfoEntry 1 }

    
    hwXQoSCpcarPassededBytes OBJECT-TYPE
        SYNTAX Counter64
        MAX-ACCESS read-only
        STATUS current
        DESCRIPTION
            "Number of bytes passed of enqueue."
        ::= { hwXQoSCpcarRunInfoEntry 2 }

    
    hwXQoSCpcarTotalPackets OBJECT-TYPE
        SYNTAX Counter64
        MAX-ACCESS read-only
        STATUS current
        DESCRIPTION
            "Number of total packets."
        ::= { hwXQoSCpcarRunInfoEntry 3 }

    
    hwXQoSCpcarTotalBytes OBJECT-TYPE
        SYNTAX Counter64
        MAX-ACCESS read-only
        STATUS current
        DESCRIPTION
            "Number of total bytes."
        ::= { hwXQoSCpcarRunInfoEntry 4 }

    
    hwXQoSCpcarDiscardedPackets OBJECT-TYPE
        SYNTAX Counter64
        MAX-ACCESS read-only
        STATUS current
        DESCRIPTION
            "Number of packets discarded when enqueued by discard method."
        ::= { hwXQoSCpcarRunInfoEntry 5 }

    
    hwXQoSCpcarDiscardedBytes OBJECT-TYPE
        SYNTAX Counter64
        MAX-ACCESS read-only
        STATUS current
        DESCRIPTION
            "Number of bytes discarded when enqueued by discard method."
        ::= { hwXQoSCpcarRunInfoEntry 6 }

    -- 1.3.6.1.4.1.2011.5.25.32.4.1.4.2.2
    hwXQoSCpCarSlotStatTable OBJECT-TYPE
        SYNTAX SEQUENCE OF HwXQoSCpCarSlotStatEntry
        MAX-ACCESS not-accessible
        STATUS current
        DESCRIPTION
            "A table of Running statistics for sample
            in a QoS policy applied on the slot."
        ::= { hwXQoSCpcarStaticsObjects 2 }
    
    -- 1.3.6.1.4.1.2011.5.25.32.4.1.4.2.2.1
    hwXQoSCpCarSlotStatEntry OBJECT-TYPE
        SYNTAX HwXQoSCpCarSlotStatEntry
        MAX-ACCESS not-accessible
        STATUS current
        DESCRIPTION
            "Cp car on the slot statistics entry."
        INDEX { hwXQoSCpCarSlotStatSlotIndex, hwXQoSCpCarSlotStatPacketType }
        ::= { hwXQoSCpCarSlotStatTable 1 }
    
    HwXQoSCpCarSlotStatEntry ::=
        SEQUENCE { 
            hwXQoSCpCarSlotStatSlotIndex
                Integer32,
            hwXQoSCpCarSlotStatPacketType
                Integer32,
            hwXQoSCpCarSlotStatDiscardedPackets
                Counter64,
            hwXQoSCpCarSlotStatDiscardedBytes
                Counter64,
            hwXQoSCpCarSlotStatPassedPackets
                Counter64,
            hwXQoSCpCarSlotStatPassededBytes
                Counter64,
            hwXQoSCpCarSlotStatTotalPackets
                Counter64,
            hwXQoSCpCarSlotStatTotalBytes
                Counter64
         }

    -- 1.3.6.1.4.1.2011.5.25.32.4.1.4.2.2.1.1
    hwXQoSCpCarSlotStatSlotIndex OBJECT-TYPE
        SYNTAX Integer32
        MAX-ACCESS not-accessible
        STATUS current
        DESCRIPTION
            "Slot index."
        ::= { hwXQoSCpCarSlotStatEntry 1 }
    
    -- 1.3.6.1.4.1.2011.5.25.32.4.1.4.2.2.1.2
    hwXQoSCpCarSlotStatPacketType OBJECT-TYPE
        SYNTAX Integer32
        MAX-ACCESS not-accessible
        STATUS current
        DESCRIPTION
            "Packet type."
        ::= { hwXQoSCpCarSlotStatEntry 2 }
    
    -- 1.3.6.1.4.1.2011.5.25.32.4.1.4.2.2.1.3
    hwXQoSCpCarSlotStatDiscardedPackets OBJECT-TYPE
        SYNTAX Counter64
        MAX-ACCESS read-only
        STATUS current
        DESCRIPTION
            "Number of packets discarded."
        ::= { hwXQoSCpCarSlotStatEntry 3 }
    
    -- 1.3.6.1.4.1.2011.5.25.32.4.1.4.2.2.1.4
    hwXQoSCpCarSlotStatDiscardedBytes OBJECT-TYPE
        SYNTAX Counter64
        MAX-ACCESS read-only
        STATUS current
        DESCRIPTION
            "Number of bytes discarded."
        ::= { hwXQoSCpCarSlotStatEntry 4 }
    
    -- 1.3.6.1.4.1.2011.5.25.32.4.1.4.2.2.1.5
    hwXQoSCpCarSlotStatPassedPackets OBJECT-TYPE
        SYNTAX Counter64
        MAX-ACCESS read-only
        STATUS current
        DESCRIPTION
            "Number of packets passed."
        ::= { hwXQoSCpCarSlotStatEntry 5 }
    
    -- 1.3.6.1.4.1.2011.5.25.32.4.1.4.2.2.1.6
    hwXQoSCpCarSlotStatPassededBytes OBJECT-TYPE
        SYNTAX Counter64
        MAX-ACCESS read-only
        STATUS current
        DESCRIPTION
            "Number of bytes passed."
        ::= { hwXQoSCpCarSlotStatEntry 6 }
    
    -- 1.3.6.1.4.1.2011.5.25.32.4.1.4.2.2.1.7
    hwXQoSCpCarSlotStatTotalPackets OBJECT-TYPE
        SYNTAX Counter64
        MAX-ACCESS read-only
        STATUS current
        DESCRIPTION
            "Number of total packets."
        ::= { hwXQoSCpCarSlotStatEntry 7 }
    
    -- 1.3.6.1.4.1.2011.5.25.32.4.1.4.2.2.1.8
    hwXQoSCpCarSlotStatTotalBytes OBJECT-TYPE
        SYNTAX Counter64
        MAX-ACCESS read-only
        STATUS current
        DESCRIPTION
            "Number of total bytes."
        ::= { hwXQoSCpCarSlotStatEntry 8 }
        
--    Interface statistics information 
    hwXQoSIfStatisticsObjects OBJECT IDENTIFIER ::= { hwXQoSStatisticsObjects 3 }

    
--    CAR statistics
    hwXQoSIfCarRunInfoTable OBJECT-TYPE
        SYNTAX SEQUENCE OF HwXQoSIfCarRunInfoEntry
        MAX-ACCESS not-accessible
        STATUS current
        DESCRIPTION
            "A table of statistics for CAR on the interface."
        ::= { hwXQoSIfStatisticsObjects 1 }

    
    hwXQoSIfCarRunInfoEntry OBJECT-TYPE
        SYNTAX HwXQoSIfCarRunInfoEntry
        MAX-ACCESS not-accessible
        STATUS current
        DESCRIPTION
            "CAR statistics information entry."
        INDEX { hwXQoSIfCarIndex, hwXQoSIfVlanID }
        ::= { hwXQoSIfCarRunInfoTable 1 }

    
    HwXQoSIfCarRunInfoEntry ::=
        SEQUENCE { 
            hwXQoSIfCarIndex
                Integer32,
            hwXQoSIfVlanID
                Integer32,
            hwXQoSIfCarGreenPassedPackets
                Counter64,
            hwXQoSIfCarGreenPassedBytes
                Counter64,
            hwXQoSIfCarGreenRemarkedPackets
                Counter64,
            hwXQoSIfCarGreenRemarkedBytes
                Counter64,
            hwXQoSIfCarGreenDiscardedPackets
                Counter64,
            hwXQoSIfCarGreenDiscardedBytes
                Counter64,
            hwXQoSIfCarYellowPassedPackets
                Counter64,
            hwXQoSIfCarYellowPassedBytes
                Counter64,
            hwXQoSIfCarYellowRemarkedPackets
                Counter64,
            hwXQoSIfCarYellowRemarkedBytes
                Counter64,
            hwXQoSIfCarYellowDiscardedPackets
                Counter64,
            hwXQoSIfCarYellowDiscardedBytes
                Counter64,
            hwXQoSIfCarRedPassedPackets
                Counter64,
            hwXQoSIfCarRedPassedBytes
                Counter64,
            hwXQoSIfCarRedRemarkedPackets
                Counter64,
            hwXQoSIfCarRedRemarkedBytes
                Counter64,
            hwXQoSIfCarRedDiscardedPackets
                Counter64,
            hwXQoSIfCarRedDiscardedBytes
                Counter64,
                hwXQoSIfCarTotalDiscardPackets
                    Counter64,
                hwXQoSIfCarInBoundDiscardPackets
                    Counter64,
                hwXQoSIfCarOutBoundDiscardPackets
                Counter64
         }

    hwXQoSIfCarIndex OBJECT-TYPE
        SYNTAX Integer32
        MAX-ACCESS read-only
        STATUS current
        DESCRIPTION
            "Interface Index, equal to ifIndex."
        ::= { hwXQoSIfCarRunInfoEntry 1 }

    hwXQoSIfVlanID OBJECT-TYPE
        SYNTAX Integer32 (0 | 1..4095)
        MAX-ACCESS read-only
        STATUS current
        DESCRIPTION
            "Vlan ID.
            -1 can't be set.
            0 is the default value"
        ::= { hwXQoSIfCarRunInfoEntry 2 }

    hwXQoSIfCarGreenPassedPackets OBJECT-TYPE
        SYNTAX Counter64
        MAX-ACCESS read-only
        STATUS current
        DESCRIPTION
            "Number of green packets passed."
        ::= { hwXQoSIfCarRunInfoEntry 3 }

    
    hwXQoSIfCarGreenPassedBytes OBJECT-TYPE
        SYNTAX Counter64
        MAX-ACCESS read-only
        STATUS current
        DESCRIPTION
            "Number of bytes green packets passed."
        ::= { hwXQoSIfCarRunInfoEntry 4 }

    
    hwXQoSIfCarGreenRemarkedPackets OBJECT-TYPE
        SYNTAX Counter64
        MAX-ACCESS read-only
        STATUS current
        DESCRIPTION
            "Number of green remarked packets."
        ::= { hwXQoSIfCarRunInfoEntry 5 }

    
    hwXQoSIfCarGreenRemarkedBytes OBJECT-TYPE
        SYNTAX Counter64
        MAX-ACCESS read-only
        STATUS current
        DESCRIPTION
            "Number of bytes green packets remarked."
        ::= { hwXQoSIfCarRunInfoEntry 6 }

    
    hwXQoSIfCarGreenDiscardedPackets OBJECT-TYPE
        SYNTAX Counter64
        MAX-ACCESS read-only
        STATUS current
        DESCRIPTION
            "Number of packets discarded."
        ::= { hwXQoSIfCarRunInfoEntry 7 }

    
    hwXQoSIfCarGreenDiscardedBytes OBJECT-TYPE
        SYNTAX Counter64
        MAX-ACCESS read-only
        STATUS current
        DESCRIPTION
            "Number of bytes exceeding CIR."
        ::= { hwXQoSIfCarRunInfoEntry 8 }

    hwXQoSIfCarYellowPassedPackets OBJECT-TYPE
        SYNTAX Counter64
        MAX-ACCESS read-only
        STATUS current
        DESCRIPTION
            "Number of yellow packets passed."
        ::= { hwXQoSIfCarRunInfoEntry 9 }

    
    hwXQoSIfCarYellowPassedBytes OBJECT-TYPE
        SYNTAX Counter64
        MAX-ACCESS read-only
        STATUS current
        DESCRIPTION
            "Number of bytes yellow packets passed."
        ::= { hwXQoSIfCarRunInfoEntry 10 }

    
    hwXQoSIfCarYellowRemarkedPackets OBJECT-TYPE
        SYNTAX Counter64
        MAX-ACCESS read-only
        STATUS current
        DESCRIPTION
            "Number of yellow remarked packets."
        ::= { hwXQoSIfCarRunInfoEntry 11 }

    
    hwXQoSIfCarYellowRemarkedBytes OBJECT-TYPE
        SYNTAX Counter64
        MAX-ACCESS read-only
        STATUS current
        DESCRIPTION
            "Number of bytes yellow packets remarked."
        ::= { hwXQoSIfCarRunInfoEntry 12 }

    
    hwXQoSIfCarYellowDiscardedPackets OBJECT-TYPE
        SYNTAX Counter64
        MAX-ACCESS read-only
        STATUS current
        DESCRIPTION
            "Number of yellow discard packets."
        ::= { hwXQoSIfCarRunInfoEntry 13 }

    
    hwXQoSIfCarYellowDiscardedBytes OBJECT-TYPE
        SYNTAX Counter64
        MAX-ACCESS read-only
        STATUS current
        DESCRIPTION
            "Number of bytes exceeding CIR."
        ::= { hwXQoSIfCarRunInfoEntry 14 }

    hwXQoSIfCarRedPassedPackets OBJECT-TYPE
        SYNTAX Counter64
        MAX-ACCESS read-only
        STATUS current
        DESCRIPTION
            "Number of red passed packets."
        ::= { hwXQoSIfCarRunInfoEntry 15 }

    
    hwXQoSIfCarRedPassedBytes OBJECT-TYPE
        SYNTAX Counter64
        MAX-ACCESS read-only
        STATUS current
        DESCRIPTION
            "Number of red passed  bytes."
        ::= { hwXQoSIfCarRunInfoEntry 16 }

    
    hwXQoSIfCarRedRemarkedPackets OBJECT-TYPE
        SYNTAX Counter64
        MAX-ACCESS read-only
        STATUS current
        DESCRIPTION
            "Number of red remarked packets."
        ::= { hwXQoSIfCarRunInfoEntry 17 }

    
    hwXQoSIfCarRedRemarkedBytes OBJECT-TYPE
        SYNTAX Counter64
        MAX-ACCESS read-only
        STATUS current
        DESCRIPTION
            "Number of red remarked bytes."
        ::= { hwXQoSIfCarRunInfoEntry 18 }

    
    hwXQoSIfCarRedDiscardedPackets OBJECT-TYPE
        SYNTAX Counter64
        MAX-ACCESS read-only
        STATUS current
        DESCRIPTION
            "Number of red discareded packets."
        ::= { hwXQoSIfCarRunInfoEntry 19 }

    
    hwXQoSIfCarRedDiscardedBytes OBJECT-TYPE
        SYNTAX Counter64
        MAX-ACCESS read-only
        STATUS current
        DESCRIPTION
            "Number of bytes exceeding CIR."
        ::= { hwXQoSIfCarRunInfoEntry 20 }
    
        -- 1.3.6.1.4.1.2011.5.25.32.4.1.4.3.1.1.21
        hwXQoSIfCarTotalDiscardPackets OBJECT-TYPE
            SYNTAX Counter64
            MAX-ACCESS read-only
            STATUS current
            DESCRIPTION
                "Number of total discard packets."
            ::= { hwXQoSIfCarRunInfoEntry 21 }
        
        -- 1.3.6.1.4.1.2011.5.25.32.4.1.4.3.1.1.22
        hwXQoSIfCarInBoundDiscardPackets OBJECT-TYPE
            SYNTAX Counter64
            MAX-ACCESS read-only
            STATUS current
            DESCRIPTION
                "Number of inbound direction discard packets."
            ::= { hwXQoSIfCarRunInfoEntry 22 }
        
        -- 1.3.6.1.4.1.2011.5.25.32.4.1.4.3.1.1.23
        hwXQoSIfCarOutBoundDiscardPackets OBJECT-TYPE
            SYNTAX Counter64
            MAX-ACCESS read-only
            STATUS current
            DESCRIPTION
                "Number of outbound direction discard packets."
            ::= { hwXQoSIfCarRunInfoEntry 23 }
                
--    Queue statistics
    hwXQoSIfQueueRunInfoTable OBJECT-TYPE
        SYNTAX SEQUENCE OF HwXQoSIfQueueRunInfoEntry
        MAX-ACCESS not-accessible
        STATUS current
        DESCRIPTION
            "A table of Running statistics for queue
            in a QoS policy applied on the interface."
        ::= { hwXQoSIfStatisticsObjects 3 }

    
    hwXQoSIfQueueRunInfoEntry OBJECT-TYPE
        SYNTAX HwXQoSIfQueueRunInfoEntry
        MAX-ACCESS not-accessible
        STATUS current
        DESCRIPTION
            "Queue statistics entry."
        INDEX { hwXQoSIfQueueIfIndex, hwXQoSIfQueueVlanID, hwXQoSIfQueueCosType }
        ::= { hwXQoSIfQueueRunInfoTable 1 }

    
    HwXQoSIfQueueRunInfoEntry ::=
        SEQUENCE { 
            hwXQoSIfQueueIfIndex
                Integer32,
            hwXQoSIfQueueVlanID
                Integer32, 
            hwXQoSIfQueueCosType
                CosType,
            hwXQoSIfQueuePassedPackets
                Counter64,
            hwXQoSIfQueuePassededBytes
                Counter64,
            hwXQoSIfQueueTotalPackets
                Counter64,
            hwXQoSIfQueueTotalBytes
                Counter64,
            hwXQoSIfQueueDiscardedPackets
                Counter64,
            hwXQoSIfQueueDiscardedBytes
                Counter64,
            hwXQoSIfQueuePassedPacketRate
                Counter64,
            hwXQoSIfQueuePassedByteRate
                Counter64,
            hwXQoSIfQueueDiscardedPacketRate 
                Counter64,
            hwXQoSIfQueueDiscardedByteRate
                Counter64,
            hwXQoSIfQueueResetFlag
                ResetFlag,
            hwXQoSIfQueueUsagePercentage
                Integer32, 
-- BEGIN: Added by l00248629, 2013/12/13
            hwXQoSIfQueueDropTailDiscardedPackets
                Counter64,
            hwXQoSIfQueueDropTailDiscardedBytes
                Counter64,      
            hwXQoSIfQueueWredDiscardedPackets
                Counter64,      
            hwXQoSIfQueueWredDiscardedBytes
                Counter64,      
            hwXQoSIfQueueDropTailDiscardedPacketRate
                Counter64,      
            hwXQoSIfQueueDropTailDiscardedByteRate
                Counter64,      
            hwXQoSIfQueueWredDiscardedPacketRate
                Counter64,      
            hwXQoSIfQueueWredDiscardedByteRate
                Counter64,  
           hwXQoSIfQueueStatisticsTrafficTowardThisPort
                Counter64,
           hwXQoSIfQueueStatisticsPhysicalBandwidthOfPortQoS
                Counter64
-- END: Added by l00248629, 2013/12/13                                                 
         }

    hwXQoSIfQueueIfIndex OBJECT-TYPE
        SYNTAX Integer32
        MAX-ACCESS read-only
        STATUS current
        DESCRIPTION
            "The value of this object identifies the interface index."
        ::= { hwXQoSIfQueueRunInfoEntry 1 }

    hwXQoSIfQueueVlanID OBJECT-TYPE
        SYNTAX Integer32 (0 | 1..4095)
        MAX-ACCESS read-only
        STATUS current
        DESCRIPTION
            "Vlan ID.
            -1 can't be set.
            0 is the default value"
        ::= { hwXQoSIfQueueRunInfoEntry 2 }


    hwXQoSIfQueueCosType OBJECT-TYPE
        SYNTAX CosType
        MAX-ACCESS read-only
        STATUS current
        DESCRIPTION
            "The value of this object identifies COS of the queue.The value can be any of the following:CS7(8),CS6(7),EF(6)
AF4(5),AF3(4),AF2(3),AF1(2),BE(1)."
        ::= { hwXQoSIfQueueRunInfoEntry 3 }


    hwXQoSIfQueuePassedPackets OBJECT-TYPE
        SYNTAX Counter64
        MAX-ACCESS read-only
        STATUS current
        DESCRIPTION
            "This object indicates the number of packets that pass the queue."
        ::= { hwXQoSIfQueueRunInfoEntry 4 }

    
    hwXQoSIfQueuePassededBytes OBJECT-TYPE
        SYNTAX Counter64
        MAX-ACCESS read-only
        STATUS current
        DESCRIPTION
            "This object indicates the number of bytes that pass the queue.The object has no default value."
        ::= { hwXQoSIfQueueRunInfoEntry 5 }

    
    hwXQoSIfQueueTotalPackets OBJECT-TYPE
        SYNTAX Counter64
        MAX-ACCESS read-only
        STATUS current
        DESCRIPTION
            "This object indicates the number of packets that reach the queue.The object has no default value."
        ::= { hwXQoSIfQueueRunInfoEntry 6 }

    
    hwXQoSIfQueueTotalBytes OBJECT-TYPE
        SYNTAX Counter64
        MAX-ACCESS read-only
        STATUS current
        DESCRIPTION
            "This object indicates the number of bytes that reach the queue.The object has no default value."
        ::= { hwXQoSIfQueueRunInfoEntry 7 }

    
    hwXQoSIfQueueDiscardedPackets OBJECT-TYPE
        SYNTAX Counter64
        MAX-ACCESS read-only
        STATUS current
        DESCRIPTION
            "This object indicates the number of discarded packets.The object has no default value."
        ::= { hwXQoSIfQueueRunInfoEntry 8 }

    
    hwXQoSIfQueueDiscardedBytes OBJECT-TYPE
        SYNTAX Counter64
        MAX-ACCESS read-only
        STATUS current
        DESCRIPTION
            "This object indicates the number of discarded bytes.The object has no default value."
        ::= { hwXQoSIfQueueRunInfoEntry 9 }

    hwXQoSIfQueuePassedPacketRate OBJECT-TYPE
        SYNTAX Counter64
        MAX-ACCESS read-only
        STATUS current
        DESCRIPTION
            "This object indicates the packet rate, in pps.The object has no default value."
        ::= { hwXQoSIfQueueRunInfoEntry 10 }

    hwXQoSIfQueuePassedByteRate OBJECT-TYPE
        SYNTAX Counter64
        MAX-ACCESS read-only
        STATUS current
        DESCRIPTION
            "This object indicates the byte rate, in bps.The object has no default value."
        ::= { hwXQoSIfQueueRunInfoEntry 11 }
        
    hwXQoSIfQueueDiscardedPacketRate OBJECT-TYPE
        SYNTAX Counter64
        MAX-ACCESS read-only
        STATUS current
        DESCRIPTION
            "This object indicates the packet rate of discarded packets, in pps.The object has no default value."
        ::= { hwXQoSIfQueueRunInfoEntry 12 }

    hwXQoSIfQueueDiscardedByteRate OBJECT-TYPE
        SYNTAX Counter64
        MAX-ACCESS read-only
        STATUS current
        DESCRIPTION
            "This object indicates the byte rate of discarded packets, in bps.The object has no default value."
        ::= { hwXQoSIfQueueRunInfoEntry 13 }         
        
     hwXQoSIfQueueResetFlag OBJECT-TYPE
        SYNTAX ResetFlag
        MAX-ACCESS read-write
        STATUS current
        DESCRIPTION
            "Reset queue statistics information."
        ::= { hwXQoSIfQueueRunInfoEntry 14 }

     hwXQoSIfQueueUsagePercentage OBJECT-TYPE
        SYNTAX Integer32
        MAX-ACCESS read-only
        STATUS current
        DESCRIPTION
            "This object indicates the usage percentage of queue.The object has no default value."
        ::= { hwXQoSIfQueueRunInfoEntry 15 } 
        
-- BEGIN: Added by l00248629, 2013/12/13
      hwXQoSIfQueueDropTailDiscardedPackets OBJECT-TYPE
            SYNTAX  Counter64
            MAX-ACCESS read-only
            STATUS current
            DESCRIPTION
            " The value of this object identifies the number of discarded tail packets. "    
            ::= { hwXQoSIfQueueRunInfoEntry 16 }          

      hwXQoSIfQueueDropTailDiscardedBytes OBJECT-TYPE
            SYNTAX  Counter64
            MAX-ACCESS read-only
            STATUS current
            DESCRIPTION
            " The value of this object identifies the number of discarded tail bytes. "    
            ::= { hwXQoSIfQueueRunInfoEntry 17 }      

      hwXQoSIfQueueWredDiscardedPackets OBJECT-TYPE
            SYNTAX  Counter64
            MAX-ACCESS read-only
            STATUS current
            DESCRIPTION
            " The value of this object identifies the number of packets that are discarded by WRED. "    
            ::= { hwXQoSIfQueueRunInfoEntry 18 } 
 
      hwXQoSIfQueueWredDiscardedBytes OBJECT-TYPE
            SYNTAX  Counter64
            MAX-ACCESS read-only
            STATUS current
            DESCRIPTION
            " The value of this object identifies the number of bytes that are discarded by WRED. "    
            ::= { hwXQoSIfQueueRunInfoEntry 19 } 
            
      hwXQoSIfQueueDropTailDiscardedPacketRate OBJECT-TYPE
            SYNTAX  Counter64
            MAX-ACCESS read-only
            STATUS current
            DESCRIPTION
            " This object indicates the tail packet discarding rate. "    
            ::= { hwXQoSIfQueueRunInfoEntry 20 }  
            
      hwXQoSIfQueueDropTailDiscardedByteRate OBJECT-TYPE
            SYNTAX  Counter64
            MAX-ACCESS read-only
            STATUS current
            DESCRIPTION
            " This object indicates the tail byte discarding rate. "    
            ::= { hwXQoSIfQueueRunInfoEntry 21 }  

      hwXQoSIfQueueWredDiscardedPacketRate OBJECT-TYPE
            SYNTAX  Counter64
            MAX-ACCESS read-only
            STATUS current
            DESCRIPTION
            " This object indicates the WRED packet discarding rate."    
            ::= { hwXQoSIfQueueRunInfoEntry 22 }  

      hwXQoSIfQueueWredDiscardedByteRate OBJECT-TYPE
            SYNTAX  Counter64
            MAX-ACCESS read-only
            STATUS current
            DESCRIPTION
            " This object indicates the WRED byte discarding rate."    
            ::= { hwXQoSIfQueueRunInfoEntry 23 }   

      hwXQoSIfQueueStatisticsTrafficTowardThisPort OBJECT-TYPE
            SYNTAX  Counter64
            MAX-ACCESS read-only
            STATUS current
            DESCRIPTION
            " This object indicates the traffic which towards this port."    
            ::= { hwXQoSIfQueueRunInfoEntry 24 }   

      hwXQoSIfQueueStatisticsPhysicalBandwidthOfPortQoS OBJECT-TYPE
            SYNTAX  Counter64
            MAX-ACCESS read-only
            STATUS current
            DESCRIPTION
            " This object indicates the physical bandwidth of port QoS."    
            ::= { hwXQoSIfQueueRunInfoEntry 25 }    
-- END: Added by l00248629, 2013/12/13                                                 
       
--    WRED statistics            
    hwXQoSIfWredRunInfoTable OBJECT-TYPE
        SYNTAX SEQUENCE OF HwXQoSIfWredRunInfoEntry
        MAX-ACCESS not-accessible
        STATUS current
        DESCRIPTION
            "A table of Running statistics for WRED
            in a QoS policy applied on the interface."
        ::= { hwXQoSIfStatisticsObjects 4 }

    
    hwXQoSIfWredRunInfoEntry OBJECT-TYPE
        SYNTAX HwXQoSIfWredRunInfoEntry
        MAX-ACCESS not-accessible
        STATUS current
        DESCRIPTION
            "WRED statistics entry."
        INDEX { hwXQoSIfWredIfIndex, hwXQoSIfWredVlanID }
        ::= { hwXQoSIfWredRunInfoTable 1 }

    
    HwXQoSIfWredRunInfoEntry ::=
        SEQUENCE { 
            hwXQoSIfWredIfIndex
                Integer32,
            hwXQoSIfWredVlanID
                Integer32,
            hwXQoSIfWredRandomDiscardedPackets
                Counter64,
            hwXQoSIfWredTailDiscardedPackets
                Counter64,
            hwXQoSIfWredDiscardedPackets
                Counter64
         }

    hwXQoSIfWredIfIndex OBJECT-TYPE
        SYNTAX Integer32
        MAX-ACCESS read-only
        STATUS current
        DESCRIPTION
            "Index of interface."
        ::= { hwXQoSIfWredRunInfoEntry 1 }

    hwXQoSIfWredVlanID OBJECT-TYPE
        SYNTAX Integer32 (0 | 1..4095)
        MAX-ACCESS read-only
        STATUS current
        DESCRIPTION
            "Vlan ID.
            -1 can't be set.
            0 is the default value"
        ::= { hwXQoSIfWredRunInfoEntry 2 }

    hwXQoSIfWredRandomDiscardedPackets OBJECT-TYPE
        SYNTAX Counter64
        MAX-ACCESS read-only
        STATUS current
        DESCRIPTION
            "Number of packets that random-discarded by WRED."
        ::= { hwXQoSIfWredRunInfoEntry 3 }

    
    hwXQoSIfWredTailDiscardedPackets OBJECT-TYPE
        SYNTAX Counter64
        MAX-ACCESS read-only
        STATUS current
        DESCRIPTION
            "Number of packets that tail-discarded by WRED."
        ::= { hwXQoSIfWredRunInfoEntry 4 }

    hwXQoSIfWredDiscardedPackets OBJECT-TYPE
        SYNTAX Counter64
        MAX-ACCESS read-only
        STATUS current
        DESCRIPTION
            "Number of packets that discarded by WRED.
            Include random-discarded and tail-discarded"
        ::= { hwXQoSIfWredRunInfoEntry 5 }
        
--    LR statistics            
    hwXQoSIfLrRunInfoTable OBJECT-TYPE
        SYNTAX SEQUENCE OF HwXQoSIfLrRunInfoEntry
        MAX-ACCESS not-accessible
        STATUS current
        DESCRIPTION
            "A table of Running statistics for LR
            in a QoS policy applied on the interface."
        ::= { hwXQoSIfStatisticsObjects 5 }

    
    hwXQoSIfLrRunInfoEntry OBJECT-TYPE
        SYNTAX HwXQoSIfLrRunInfoEntry
        MAX-ACCESS not-accessible
        STATUS current
        DESCRIPTION
            "LR statistics entry."
        INDEX { hwXQoSIfLrIfIndex, hwXQoSIfLrVlanID }
        ::= { hwXQoSIfLrRunInfoTable 1 }

    
    HwXQoSIfLrRunInfoEntry ::=
        SEQUENCE { 
            hwXQoSIfLrIfIndex
                Integer32,
            hwXQoSIfLrVlanID
                Integer32,
            hwXQoSIfLrPassedPackets
                Counter64,
            hwXQoSIfLrPassedBytes
                Counter64,
            hwXQoSIfLrDiscardedPackets
                Counter64,
            hwXQoSIfLrDiscardedBytes
                Counter64,
            hwXQoSIfLrDelayedPackets
                Counter64,
            hwXQoSIfLrDelayedBytes
                Counter64
         }

    hwXQoSIfLrIfIndex OBJECT-TYPE
        SYNTAX Integer32
        MAX-ACCESS read-only
        STATUS current
        DESCRIPTION
            "Index of Interface of LR."
        ::= { hwXQoSIfLrRunInfoEntry 1 }

    hwXQoSIfLrVlanID OBJECT-TYPE
        SYNTAX Integer32 (0 | 1..4095)
        MAX-ACCESS read-only
        STATUS current
        DESCRIPTION
            "Vlan ID.
            -1 can't be set.
            0 is the default value"
        ::= { hwXQoSIfLrRunInfoEntry 2 }

    hwXQoSIfLrPassedPackets OBJECT-TYPE
        SYNTAX Counter64
        MAX-ACCESS read-only
        STATUS current
        DESCRIPTION
            "Number of packets passed by LR."
        ::= { hwXQoSIfLrRunInfoEntry 3 }

    
    hwXQoSIfLrPassedBytes OBJECT-TYPE
        SYNTAX Counter64
        MAX-ACCESS read-only
        STATUS current
        DESCRIPTION
            "Number of bytes passed by LR."
        ::= { hwXQoSIfLrRunInfoEntry 4 }

    
    hwXQoSIfLrDiscardedPackets OBJECT-TYPE
        SYNTAX Counter64
        MAX-ACCESS read-only
        STATUS current
        DESCRIPTION
            "Number of packets discarded by LR."
        ::= { hwXQoSIfLrRunInfoEntry 5 }

    
    hwXQoSIfLrDiscardedBytes OBJECT-TYPE
        SYNTAX Counter64
        MAX-ACCESS read-only
        STATUS current
        DESCRIPTION
            "Number of bytes discarded by LR."
        ::= { hwXQoSIfLrRunInfoEntry 6 }

    
    hwXQoSIfLrDelayedPackets OBJECT-TYPE
        SYNTAX Counter64
        MAX-ACCESS read-only
        STATUS current
        DESCRIPTION
            "Number of packets delayed by LR."
        ::= { hwXQoSIfLrRunInfoEntry 7 }

    
    hwXQoSIfLrDelayedBytes OBJECT-TYPE
        SYNTAX Counter64
        MAX-ACCESS read-only
        STATUS current
        DESCRIPTION
            "Number of bytes delayed by LR."
        ::= { hwXQoSIfLrRunInfoEntry 8 }

--    Mirror statistics            
    hwXQoSIfMirrorRunInfoTable OBJECT-TYPE
        SYNTAX SEQUENCE OF HwXQoSIfMirrorRunInfoEntry
        MAX-ACCESS not-accessible
        STATUS current
        DESCRIPTION
            "A table of Running statistics for mirror
            in a QoS policy applied on the interface."
        ::= { hwXQoSIfStatisticsObjects 6 }

    
    hwXQoSIfMirrorRunInfoEntry OBJECT-TYPE
        SYNTAX HwXQoSIfMirrorRunInfoEntry
        MAX-ACCESS not-accessible
        STATUS current
        DESCRIPTION
            "Mirror statistics entry."
        INDEX { hwXQoSIfMirrorIfIndex, hwXQoSIfMirrorVlanID }
        ::= { hwXQoSIfMirrorRunInfoTable 1 }

    
    HwXQoSIfMirrorRunInfoEntry ::=
        SEQUENCE { 
            hwXQoSIfMirrorIfIndex
                Integer32,
            hwXQoSIfMirrorVlanID
                Integer32,
            hwXQoSIfMirroredPackets
                Counter64
         }

    hwXQoSIfMirrorIfIndex OBJECT-TYPE
        SYNTAX Integer32
        MAX-ACCESS read-only
        STATUS current
        DESCRIPTION
            "Index of interface mirror."
        ::= { hwXQoSIfMirrorRunInfoEntry 1 }

    hwXQoSIfMirrorVlanID OBJECT-TYPE
        SYNTAX Integer32 (0 | 1..4095)
        MAX-ACCESS read-only
        STATUS current
        DESCRIPTION
            "Vlan ID.
            -1 can't be set.
            0 is the default value"
        ::= { hwXQoSIfMirrorRunInfoEntry 2 }

    hwXQoSIfMirroredPackets OBJECT-TYPE
        SYNTAX Counter64
        MAX-ACCESS read-only
        STATUS current
        DESCRIPTION
            "Number of packets Mirrored."
        ::= { hwXQoSIfMirrorRunInfoEntry 3 }

--    Urpf statistics            
    hwXQoSIfUrpfRunInfoTable OBJECT-TYPE
        SYNTAX SEQUENCE OF HwXQoSIfUrpfRunInfoEntry
        MAX-ACCESS not-accessible
        STATUS current
        DESCRIPTION
            "A table of Running statistics for urpf
            in a QoS policy applied on the interface."
        ::= { hwXQoSIfStatisticsObjects 7 }

    
    hwXQoSIfUrpfRunInfoEntry OBJECT-TYPE
        SYNTAX HwXQoSIfUrpfRunInfoEntry
        MAX-ACCESS not-accessible
        STATUS current
        DESCRIPTION
            "Urpf statistics entry."
        INDEX { hwXQoSIfUrpfIfIndex, hwXQoSIfUrpfVlanID }
        ::= { hwXQoSIfUrpfRunInfoTable 1 }

    
    HwXQoSIfUrpfRunInfoEntry ::=
        SEQUENCE { 
            hwXQoSIfUrpfIfIndex
                Integer32,
            hwXQoSIfUrpfVlanID
                Integer32,
            hwXQoSIfUrpfPassedPackets
                Counter64,
            hwXQoSIfUrpfDroppdPackets
                Counter64
         }

    hwXQoSIfUrpfIfIndex OBJECT-TYPE
        SYNTAX Integer32
        MAX-ACCESS read-only
        STATUS current
        DESCRIPTION
            "Index of interface URPF."
        ::= { hwXQoSIfUrpfRunInfoEntry 1 }

    hwXQoSIfUrpfVlanID OBJECT-TYPE
        SYNTAX Integer32 (0 | 1..4095)
        MAX-ACCESS read-only
        STATUS current
        DESCRIPTION
            "Vlan ID.
            -1 can't be set.
            0 is the default value"
        ::= { hwXQoSIfUrpfRunInfoEntry 2 }

    hwXQoSIfUrpfPassedPackets OBJECT-TYPE
        SYNTAX Counter64
        MAX-ACCESS read-only
        STATUS current
        DESCRIPTION
            "Number of packets passed."
        ::= { hwXQoSIfUrpfRunInfoEntry 3 }

    
    hwXQoSIfUrpfDroppdPackets OBJECT-TYPE
        SYNTAX Counter64
        MAX-ACCESS read-only
        STATUS current
        DESCRIPTION
            "Number of packets dropped."
        ::= { hwXQoSIfUrpfRunInfoEntry 4 }

--    Sample statistics            
    hwXQoSIfSampleRunInfoTable OBJECT-TYPE
        SYNTAX SEQUENCE OF HwXQoSIfSampleRunInfoEntry
        MAX-ACCESS not-accessible
        STATUS current
        DESCRIPTION
            "A table of Running statistics for sample
            in a QoS policy applied on the interface."
        ::= { hwXQoSIfStatisticsObjects 8 }

    
    hwXQoSIfSampleRunInfoEntry OBJECT-TYPE
        SYNTAX HwXQoSIfSampleRunInfoEntry
        MAX-ACCESS not-accessible
        STATUS current
        DESCRIPTION
            "Sample statistics entry."
        INDEX { hwXQoSIfSampleIfIndex, hwXQoSIfSampleVlanID }
        ::= { hwXQoSIfSampleRunInfoTable 1 }

    
    HwXQoSIfSampleRunInfoEntry ::=
        SEQUENCE { 
            hwXQoSIfSampleIfIndex
                Integer32,
            hwXQoSIfSampleVlanID
                Integer32,
            hwXQoSIfSampledPackets
                Counter64
         }

    hwXQoSIfSampleIfIndex OBJECT-TYPE
        SYNTAX Integer32
        MAX-ACCESS read-only
        STATUS current
        DESCRIPTION
            "Index of interface Sample."
        ::= { hwXQoSIfSampleRunInfoEntry 1 }

    hwXQoSIfSampleVlanID OBJECT-TYPE
        SYNTAX Integer32 (0 | 1..4095)
        MAX-ACCESS read-only
        STATUS current
        DESCRIPTION
            "Vlan ID.
            -1 can't be set.
            0 is the default value"
        ::= { hwXQoSIfSampleRunInfoEntry 2 }

    hwXQoSIfSampledPackets OBJECT-TYPE
        SYNTAX Counter64
        MAX-ACCESS read-only
        STATUS current
        DESCRIPTION
            "Number of packets Sampled."
        ::= { hwXQoSIfSampleRunInfoEntry 3 }

-- CAR statistics
    hwXQoSIfCarStatisticsTable OBJECT-TYPE
    SYNTAX SEQUENCE OF HwXQoSIfCarStatisticsEntry
    MAX-ACCESS not-accessible
    STATUS current
    DESCRIPTION
        "A table of CAR statistics for port-based traffic."
    ::= { hwXQoSIfStatisticsObjects 9 }

    hwXQoSIfCarStatisticsEntry OBJECT-TYPE
    SYNTAX HwXQoSIfCarStatisticsEntry
    MAX-ACCESS not-accessible
    STATUS current
    DESCRIPTION
        "A table of CAR statistics for port-based traffic, including 
        the statistics of  packets that have the rate within CIR, of 
        CIR, of PIR or exceeds PIR. ."
    INDEX { hwXQoSIfCarCfgIfIndex, hwXQoSIfCarVlanID,
        hwXQoSIfCarDirection }
    ::= { hwXQoSIfCarStatisticsTable 1 }

    HwXQoSIfCarStatisticsEntry ::=
        SEQUENCE {
            hwXQoSIfCarConformedPackets
                Counter64,
            hwXQoSIfCarConformedBytes
                Counter64,
            hwXQoSIfCarConformedPacketRate
                Counter64,
            hwXQoSIfCarConformedByteRate
                Counter64,
            hwXQoSIfCarExceededPackets
                Counter64,
            hwXQoSIfCarExceededBytes
                Counter64,
            hwXQoSIfCarExceededPacketRate
                Counter64,
            hwXQoSIfCarExceededByteRate
                Counter64,
            hwXQoSIfCarOverflowPackets
                Counter64,
            hwXQoSIfCarOverflowBytes
                Counter64,
            hwXQoSIfCarOverflowPacketRate
                Counter64,
            hwXQoSIfCarOverflowByteRate
                Counter64,
            hwXQoSIfCarPassedPackets
                Counter64,
            hwXQoSIfCarPassedBytes
                Counter64,
            hwXQoSIfCarDiscardedPackets
                Counter64,
            hwXQoSIfCarDiscardedBytes
                Counter64
         }

    hwXQoSIfCarConformedPackets OBJECT-TYPE
        SYNTAX Counter64
        MAX-ACCESS read-only
        STATUS current
        DESCRIPTION
            "This object indicates the number of packets within CIR."
        ::= { hwXQoSIfCarStatisticsEntry 11 }

    hwXQoSIfCarConformedBytes OBJECT-TYPE
        SYNTAX Counter64
        MAX-ACCESS read-only
        STATUS current
        DESCRIPTION
            "This object indicates the number of bytes within CIR."
        ::= { hwXQoSIfCarStatisticsEntry 12 }

    hwXQoSIfCarConformedPacketRate OBJECT-TYPE
        SYNTAX Counter64
        MAX-ACCESS read-only
        STATUS current
        DESCRIPTION
            "This object indicates the packet rate within CIR, in pps."
        ::= { hwXQoSIfCarStatisticsEntry 13 }

    hwXQoSIfCarConformedByteRate OBJECT-TYPE
        SYNTAX Counter64
        MAX-ACCESS read-only
        STATUS current
        DESCRIPTION
            "This object indicates the byte rate within CIR, in bps."
        ::= { hwXQoSIfCarStatisticsEntry 14 }

    hwXQoSIfCarExceededPackets OBJECT-TYPE
        SYNTAX Counter64
        MAX-ACCESS read-only
        STATUS current
        DESCRIPTION
            "This object indicates the number of packets between PIR and CIR."
        ::= { hwXQoSIfCarStatisticsEntry 15 }

    hwXQoSIfCarExceededBytes OBJECT-TYPE
        SYNTAX Counter64
        MAX-ACCESS read-only
        STATUS current
        DESCRIPTION
            "This object indicates the number of bytes between PIR and CIR."
        ::= { hwXQoSIfCarStatisticsEntry 16 }

    hwXQoSIfCarExceededPacketRate OBJECT-TYPE
        SYNTAX Counter64
        MAX-ACCESS read-only
        STATUS current
        DESCRIPTION
            "This object indicates the packet rate between PIR and CIR, in pps."
        ::= { hwXQoSIfCarStatisticsEntry 17 }

    hwXQoSIfCarExceededByteRate OBJECT-TYPE
        SYNTAX Counter64
        MAX-ACCESS read-only
        STATUS current
        DESCRIPTION
            "This object indicates the byte rate between PIR and CIR, in pps."
        ::= { hwXQoSIfCarStatisticsEntry 18 }
        
    hwXQoSIfCarOverflowPackets OBJECT-TYPE
        SYNTAX Counter64
        MAX-ACCESS read-only
        STATUS current
        DESCRIPTION
            "This object indicates the number of packets when PIR is set."
        ::= { hwXQoSIfCarStatisticsEntry 19 }

    hwXQoSIfCarOverflowBytes OBJECT-TYPE
        SYNTAX Counter64
        MAX-ACCESS read-only
        STATUS current
        DESCRIPTION
            "This object indicates the number of bytes when PIR is set."
        ::= { hwXQoSIfCarStatisticsEntry 20 }

    hwXQoSIfCarOverflowPacketRate OBJECT-TYPE
        SYNTAX Counter64
        MAX-ACCESS read-only
        STATUS current
        DESCRIPTION
            "This object indicates the packet rate when PIR is set, in pps."
        ::= { hwXQoSIfCarStatisticsEntry 21 }

    hwXQoSIfCarOverflowByteRate OBJECT-TYPE
        SYNTAX Counter64
        MAX-ACCESS read-only
        STATUS current
        DESCRIPTION
            "This object indicates the byte rate when PIR is set, in bps."
        ::= { hwXQoSIfCarStatisticsEntry 22 }

    hwXQoSIfCarPassedPackets OBJECT-TYPE
        SYNTAX Counter64
        MAX-ACCESS read-only
        STATUS current
        DESCRIPTION
            "This object indicates the number of passed packets after CAR is set."
        ::= { hwXQoSIfCarStatisticsEntry 23 }

    hwXQoSIfCarPassedBytes OBJECT-TYPE
        SYNTAX Counter64
        MAX-ACCESS read-only
        STATUS current
        DESCRIPTION
            "This object indicates the number of discarded packets after CAR is set."
        ::= { hwXQoSIfCarStatisticsEntry 24 }

    hwXQoSIfCarDiscardedPackets OBJECT-TYPE
        SYNTAX Counter64
        MAX-ACCESS read-only
        STATUS current
        DESCRIPTION
            "This object indicates the number of discarded packets after CAR is set."
        ::= { hwXQoSIfCarStatisticsEntry 25 }

    hwXQoSIfCarDiscardedBytes OBJECT-TYPE
        SYNTAX Counter64
        MAX-ACCESS read-only
        STATUS current
        DESCRIPTION
            "This object indicates the number of discarded bytes after CAR is set."
        ::= { hwXQoSIfCarStatisticsEntry 26 }
  
  
    hwXQoSIfOutboundQueueStatisticTable OBJECT-TYPE
    SYNTAX SEQUENCE OF HwXQoSIfOutboundQueueStatisticEntry
    MAX-ACCESS not-accessible
    STATUS current
    DESCRIPTION
        "The table provides the discard packets."
    ::= { hwXQoSIfStatisticsObjects 10 }
  
  
  
     hwXQoSIfOutboundQueueStatisticEntry OBJECT-TYPE
    SYNTAX HwXQoSIfOutboundQueueStatisticEntry
    MAX-ACCESS not-accessible
    STATUS current
    DESCRIPTION
        "The discard packets entry."
    INDEX { hwXQoSIfExtIndex, hwXQoSIfQueIndex }
    ::= { hwXQoSIfOutboundQueueStatisticTable 1 }
        
    HwXQoSIfOutboundQueueStatisticEntry ::=
    SEQUENCE { 
        hwXQoSIfExtIndex
            Unsigned32,
        hwXQoSIfQueIndex
            OCTET STRING,
        hwXQoSIfQueDiscardPackets
            Integer32
     }

    hwXQoSIfExtIndex OBJECT-TYPE
    SYNTAX Unsigned32
    MAX-ACCESS not-accessible
    STATUS current
    DESCRIPTION
        "Index for the extended interface."
    ::= { hwXQoSIfOutboundQueueStatisticEntry 1 }
        
    hwXQoSIfQueIndex OBJECT-TYPE
    SYNTAX OCTET STRING
    MAX-ACCESS not-accessible
    STATUS current
    DESCRIPTION
        "Index for the queue."
    ::= { hwXQoSIfOutboundQueueStatisticEntry 2 }
        
    hwXQoSIfQueDiscardPackets OBJECT-TYPE
    SYNTAX Integer32
    MAX-ACCESS read-only
    STATUS current
    DESCRIPTION
        "Number of discarded packets."
    ::= { hwXQoSIfOutboundQueueStatisticEntry 3 } 
    
    
  -- vlan stat
    hwXQoSVlanStatisticsObjects OBJECT IDENTIFIER ::= { hwXQoSStatisticsObjects 4 }

        
        hwXQosVlanStatTable OBJECT-TYPE
            SYNTAX SEQUENCE OF HwXQosVlanStatEntry
            MAX-ACCESS not-accessible
            STATUS current
            DESCRIPTION
                "The table contains statistics information for the vlan."
            ::= { hwXQoSVlanStatisticsObjects 1 }

        
        hwXQosVlanStatEntry OBJECT-TYPE
            SYNTAX HwXQosVlanStatEntry
            MAX-ACCESS not-accessible
            STATUS current
            DESCRIPTION
                "Entries of vlan statistics table."
            INDEX { hwXQosVlanStatVlanId }
            ::= { hwXQosVlanStatTable 1 }

        
        HwXQosVlanStatEntry ::=
            SEQUENCE { 
                hwXQosVlanStatVlanId
                    Integer32,
                hwXQosVlanStatInTotalPkts
                    Counter64,
                hwXQosVlanStatInTotalBytes
                    Counter64,
                hwXQosVlanStatOutTotalPkts
                    Counter64,
                hwXQosVlanStatOutTotalBytes
                    Counter64,
                hwXQosVlanStatInUcastPkts
                    Counter64,
                hwXQosVlanStatInUcastBytes
                    Counter64,
                hwXQosVlanStatOutUcastPkts
                    Counter64,
                hwXQosVlanStatOutUcastBytes
                    Counter64,
                hwXQosVlanStatInMcastPkts
                    Counter64,
                hwXQosVlanStatInMcastBytes
                    Counter64,
                hwXQosVlanStatOutMcastPkts
                    Counter64,
                hwXQosVlanStatOutMcastBytes
                    Counter64,
                hwXQosVlanStatInBcastPkts
                    Counter64,
                hwXQosVlanStatInBcastBytes
                    Counter64,
                hwXQosVlanStatOutBcastPkts
                    Counter64,
                hwXQosVlanStatOutBcastBytes
                    Counter64,
                hwXQosVlanStatInUnknownUcastPkts
                    Counter64,
                hwXQosVlanStatInUnknownUcastBytes
                    Counter64,
                hwXQosVlanStatResetFlag
                    EnabledStatus,
                hwXQosVlanStatInTotalPktsRate
                    Counter64,
                hwXQosVlanStatInTotalBytesRate
                    Counter64,
                hwXQosVlanStatOutTotalPktsRate
                    Counter64,
                hwXQosVlanStatOutTotalBytesRate
                    Counter64,
                hwXQosVlanStatInMcastTotalPktsRate
                    Counter64,
                hwXQosVlanStatInMcastTotalBytesRate
                    Counter64,
                hwXQosVlanStatInBcastTotalPktsRate
                    Counter64,
                hwXQosVlanStatInBcastTotalBytesRate
                    Counter64,
                hwXQosVlanStatInUnknownUcastTotalPktsRate
                    Counter64,
                hwXQosVlanStatInUnknownUcastTotalBytesRate
                    Counter64,
                hwXQosVlanStatInDropTotalPktsRate
                    Counter64,    
                hwXQosVlanStatInDropTotalBytesRate
                    Counter64,
                hwXQosVlanStatInDropPercentageTotalBytesRate
                    Counter64     
             }

        
        hwXQosVlanStatVlanId OBJECT-TYPE
            SYNTAX Integer32 (0 | 1..4094)
            MAX-ACCESS not-accessible
            STATUS current
            DESCRIPTION
                "The id of vlan."
            ::= { hwXQosVlanStatEntry 1 }

        
        
        hwXQosVlanStatInTotalPkts OBJECT-TYPE
            SYNTAX Counter64
            MAX-ACCESS read-only
            STATUS current
            DESCRIPTION
                "The number of received packets."
            ::= { hwXQosVlanStatEntry 2 }

        
        
        hwXQosVlanStatInTotalBytes OBJECT-TYPE
            SYNTAX Counter64
            MAX-ACCESS read-only
            STATUS current
            DESCRIPTION
                "The byte number of received packets."
            ::= { hwXQosVlanStatEntry 3 }

        
        
        hwXQosVlanStatOutTotalPkts OBJECT-TYPE
            SYNTAX Counter64
            MAX-ACCESS read-only
            STATUS current
            DESCRIPTION
                "The number of transmittable packets."
            ::= { hwXQosVlanStatEntry 4 }

        

        hwXQosVlanStatOutTotalBytes OBJECT-TYPE
            SYNTAX Counter64
            MAX-ACCESS read-only
            STATUS current
            DESCRIPTION
                "The byte number of transmittable packets."
            ::= { hwXQosVlanStatEntry 5 }

        
        
        hwXQosVlanStatInUcastPkts OBJECT-TYPE
            SYNTAX Counter64
            MAX-ACCESS read-only
            STATUS current
            DESCRIPTION
                "The number of received unicast packets."
            ::= { hwXQosVlanStatEntry 6 }

        
        
        hwXQosVlanStatInUcastBytes OBJECT-TYPE
            SYNTAX Counter64
            MAX-ACCESS read-only
            STATUS current
            DESCRIPTION
                "The number of received unicast packets' bytes."
            ::= { hwXQosVlanStatEntry 7 }

        
        
        hwXQosVlanStatOutUcastPkts OBJECT-TYPE
            SYNTAX Counter64
            MAX-ACCESS read-only
            STATUS current
            DESCRIPTION
                "The number of transmittable unicast packets."
            ::= { hwXQosVlanStatEntry 8 }

        
        
        hwXQosVlanStatOutUcastBytes OBJECT-TYPE
            SYNTAX Counter64
            MAX-ACCESS read-only
            STATUS current
            DESCRIPTION
                "The number of transmittable unicast packets' bytes."
            ::= { hwXQosVlanStatEntry 9 }

        
        
        hwXQosVlanStatInMcastPkts OBJECT-TYPE
            SYNTAX Counter64
            MAX-ACCESS read-only
            STATUS current
            DESCRIPTION
                "The number of received multicast packets."
            ::= { hwXQosVlanStatEntry 10 }

        
        
        hwXQosVlanStatInMcastBytes OBJECT-TYPE
            SYNTAX Counter64
            MAX-ACCESS read-only
            STATUS current
            DESCRIPTION
                "The number of received multicast packets' bytes."
            ::= { hwXQosVlanStatEntry 11 }

        
        
        hwXQosVlanStatOutMcastPkts OBJECT-TYPE
            SYNTAX Counter64
            MAX-ACCESS read-only
            STATUS current
            DESCRIPTION
                "The number of transmittable multicast packets."
            ::= { hwXQosVlanStatEntry 12 }

        
        
        hwXQosVlanStatOutMcastBytes OBJECT-TYPE
            SYNTAX Counter64
            MAX-ACCESS read-only
            STATUS current
            DESCRIPTION
                "The number of transmittable multicast packets' bytes."
            ::= { hwXQosVlanStatEntry 13 }

        
        
        hwXQosVlanStatInBcastPkts OBJECT-TYPE
            SYNTAX Counter64
            MAX-ACCESS read-only
            STATUS current
            DESCRIPTION
                "The number of received broadcast packets."
            ::= { hwXQosVlanStatEntry 14 }

        
        
        hwXQosVlanStatInBcastBytes OBJECT-TYPE
            SYNTAX Counter64
            MAX-ACCESS read-only
            STATUS current
            DESCRIPTION
                "The number of received broadcast packets' bytes."
            ::= { hwXQosVlanStatEntry 15 }

        
        
        hwXQosVlanStatOutBcastPkts OBJECT-TYPE
            SYNTAX Counter64
            MAX-ACCESS read-only
            STATUS current
            DESCRIPTION
                "The number of transmittable broadcast packets."
            ::= { hwXQosVlanStatEntry 16 }

        
        
        hwXQosVlanStatOutBcastBytes OBJECT-TYPE
            SYNTAX Counter64
            MAX-ACCESS read-only
            STATUS current
            DESCRIPTION
                "The number of transmittable broadcast packets."
            ::= { hwXQosVlanStatEntry 17 }

        
        
        hwXQosVlanStatInUnknownUcastPkts OBJECT-TYPE
            SYNTAX Counter64
            MAX-ACCESS read-only
            STATUS current
            DESCRIPTION
                "The number of received unknown broadcast packets."
            ::= { hwXQosVlanStatEntry 18 }

        
        
        hwXQosVlanStatInUnknownUcastBytes OBJECT-TYPE
            SYNTAX Counter64
            MAX-ACCESS read-only
            STATUS current
            DESCRIPTION
                "The number of received unknown broadcast packets' bytes."
            ::= { hwXQosVlanStatEntry 19 }

        
        
        hwXQosVlanStatResetFlag OBJECT-TYPE
            SYNTAX EnabledStatus
            MAX-ACCESS read-create
            STATUS current
            DESCRIPTION
                "The flag of reset."
            ::= { hwXQosVlanStatEntry 20 }
        hwXQosVlanStatInTotalPktsRate OBJECT-TYPE
            SYNTAX Counter64
            MAX-ACCESS read-only
            STATUS current
            DESCRIPTION
                "The rate of received packets."
            ::= { hwXQosVlanStatEntry 21 }

        
        
        hwXQosVlanStatInTotalBytesRate OBJECT-TYPE
            SYNTAX Counter64
            MAX-ACCESS read-only
            STATUS current
            DESCRIPTION
                "The rate of received bytes."
            ::= { hwXQosVlanStatEntry 22 }

        
        
        hwXQosVlanStatOutTotalPktsRate OBJECT-TYPE
            SYNTAX Counter64
            MAX-ACCESS read-only
            STATUS current
            DESCRIPTION
                "The rate of transmittable packets."
            ::= { hwXQosVlanStatEntry 23 }

        

        hwXQosVlanStatOutTotalBytesRate OBJECT-TYPE
            SYNTAX Counter64
            MAX-ACCESS read-only
            STATUS current
            DESCRIPTION
                "The rate of transmittable bytes."
            ::= { hwXQosVlanStatEntry 24 }

        hwXQosVlanStatInMcastTotalPktsRate OBJECT-TYPE
            SYNTAX Counter64
            MAX-ACCESS read-only
            STATUS current
            DESCRIPTION
                "The rate of transmittable packets."
            ::= { hwXQosVlanStatEntry 25 }

        

        hwXQosVlanStatInMcastTotalBytesRate OBJECT-TYPE
            SYNTAX Counter64
            MAX-ACCESS read-only
            STATUS current
            DESCRIPTION
                "The rate of transmittable bytes."
            ::= { hwXQosVlanStatEntry 26 }  
              
        hwXQosVlanStatInBcastTotalPktsRate OBJECT-TYPE
            SYNTAX Counter64
            MAX-ACCESS read-only
            STATUS current
            DESCRIPTION
                "The rate of transmittable packets."
            ::= { hwXQosVlanStatEntry 27 }

        

        hwXQosVlanStatInBcastTotalBytesRate OBJECT-TYPE
            SYNTAX Counter64
            MAX-ACCESS read-only
            STATUS current
            DESCRIPTION
                "The rate of transmittable bytes."
            ::= { hwXQosVlanStatEntry 28 }    
         
        hwXQosVlanStatInUnknownUcastTotalPktsRate OBJECT-TYPE
            SYNTAX Counter64
            MAX-ACCESS read-only
            STATUS current
            DESCRIPTION
                "The rate of transmittable packets."
            ::= { hwXQosVlanStatEntry 29 }

        

        hwXQosVlanStatInUnknownUcastTotalBytesRate OBJECT-TYPE
            SYNTAX Counter64
            MAX-ACCESS read-only
            STATUS current
            DESCRIPTION
                "The rate of transmittable bytes."
            ::= { hwXQosVlanStatEntry 30 }  
        hwXQosVlanStatInDropTotalPktsRate OBJECT-TYPE
            SYNTAX Counter64
            MAX-ACCESS read-only
            STATUS current
            DESCRIPTION
                "The rate of transmittable packets."
            ::= { hwXQosVlanStatEntry 31 }

        hwXQosVlanStatInDropTotalBytesRate OBJECT-TYPE
            SYNTAX Counter64
            MAX-ACCESS read-only
            STATUS current
            DESCRIPTION
                "The rate of transmittable bytes."
            ::= { hwXQosVlanStatEntry 32 }
        

        hwXQosVlanStatInDropPercentageTotalBytesRate OBJECT-TYPE
            SYNTAX Counter64
            MAX-ACCESS read-only
            STATUS current
            DESCRIPTION
                "The Percentage number of droped packets."
            ::= { hwXQosVlanStatEntry 33 }      
 
 --???????       
        hwXQosVlanSlotStatTable OBJECT-TYPE
            SYNTAX SEQUENCE OF HwXQosVlanSlotStatEntry
            MAX-ACCESS not-accessible
            STATUS current
            DESCRIPTION
                "The table contains statistics information for the vlan of board."
            ::= { hwXQoSVlanStatisticsObjects 2 }

        
        hwXQosVlanSlotStatEntry OBJECT-TYPE
            SYNTAX HwXQosVlanSlotStatEntry
            MAX-ACCESS not-accessible
            STATUS current
            DESCRIPTION
                "Entries of vlan statistics on board table."
            INDEX { hwXQosVlanSlotStatVlanId,hwXQosVlanSlotStatSlotId }
            ::= { hwXQosVlanSlotStatTable 1 }

        
        HwXQosVlanSlotStatEntry ::=
            SEQUENCE { 
                hwXQosVlanSlotStatVlanId
                    Integer32,
                hwXQosVlanSlotStatSlotId
                    Integer32,
                hwXQosVlanSlotStatInPkts
                    Counter64, 
                hwXQosVlanSlotStatInPktsRate
                    Counter64,                    
                hwXQosVlanSlotStatInBytes
                    Counter64,  
                hwXQosVlanSlotStatInBytesRate
                    Counter64,                   
                hwXQosVlanSlotStatOutPkts
                    Counter64,   
                hwXQosVlanSlotStatOutPktsRate
                    Counter64,                   
                hwXQosVlanSlotStatOutBytes
                    Counter64, 
                hwXQosVlanSlotStatOutBytesRate
                    Counter64,                   
                hwXQosVlanSlotStatInMcastPkts
                    Counter64, 
                hwXQosVlanSlotStatInMcastPktsRate
                    Counter64,
                hwXQosVlanSlotStatInMcastBytes
                    Counter64,   
                hwXQosVlanSlotStatInMcastBytesRate
                    Counter64,
                hwXQosVlanSlotStatInBcastPkts
                    Counter64,    
                hwXQosVlanSlotStatInBcastPktsRate
                    Counter64,                 
                hwXQosVlanSlotStatInBcastBytes
                    Counter64,    
                hwXQosVlanSlotStatInBcastBytesRate
                    Counter64,                   
                hwXQosVlanSlotStatInUnknownUcastPkts
                    Counter64,    
                hwXQosVlanSlotStatInUnknownUcastPktsRate
                    Counter64,                   
                hwXQosVlanSlotStatInUnknownUcastBytes
                    Counter64,
                hwXQosVlanSlotStatInUnknownUcastBytesRate
                    Counter64,   
                hwXQosVlanSlotStatInDropPkts
                    Counter64,    
                hwXQosVlanSlotStatInDropPktsRate
                    Counter64,                   
                hwXQosVlanSlotStatInDropBytes
                    Counter64,
                hwXQosVlanSlotStatInDropBytesRate
                    Counter64,  
                hwXQosVlanSlotStatInDropPercentageBytesRate
                    Counter64

             }

        
        hwXQosVlanSlotStatVlanId OBJECT-TYPE
            SYNTAX Integer32 (0 | 1..4094)
            MAX-ACCESS not-accessible
            STATUS current
            DESCRIPTION
                "The id of vlan."
            ::= { hwXQosVlanSlotStatEntry 1 }
            
         hwXQosVlanSlotStatSlotId OBJECT-TYPE
            SYNTAX Integer32 (0 | 1..5000)
            MAX-ACCESS not-accessible
            STATUS current
            DESCRIPTION
                "The id of slot."
            ::= { hwXQosVlanSlotStatEntry 2 }


        
 --in       
        hwXQosVlanSlotStatInPkts OBJECT-TYPE
            SYNTAX Counter64
            MAX-ACCESS read-only
            STATUS current
            DESCRIPTION
                "The number of received packets."
            ::= { hwXQosVlanSlotStatEntry 3 }
       
        hwXQosVlanSlotStatInPktsRate OBJECT-TYPE
            SYNTAX Counter64
            MAX-ACCESS read-only
            STATUS current
            DESCRIPTION
                "The rate of received packets by number."
            ::= { hwXQosVlanSlotStatEntry 4 }

        hwXQosVlanSlotStatInBytes OBJECT-TYPE
            SYNTAX Counter64
            MAX-ACCESS read-only
            STATUS current
            DESCRIPTION
                "The byte number of received packets."
            ::= { hwXQosVlanSlotStatEntry 5 }
        
        hwXQosVlanSlotStatInBytesRate OBJECT-TYPE
            SYNTAX Counter64
            MAX-ACCESS read-only
            STATUS current
            DESCRIPTION
                "The rate of received packets by bytes."
            ::= { hwXQosVlanSlotStatEntry 6 }


--out      
        
        hwXQosVlanSlotStatOutPkts OBJECT-TYPE
            SYNTAX Counter64
            MAX-ACCESS read-only
            STATUS current
            DESCRIPTION
                "The number of transmittable packets."
            ::= { hwXQosVlanSlotStatEntry 7 }
 
        hwXQosVlanSlotStatOutPktsRate OBJECT-TYPE
            SYNTAX Counter64
            MAX-ACCESS read-only
            STATUS current
            DESCRIPTION
                "The rate of transmittable packets by bytes."
            ::= { hwXQosVlanSlotStatEntry 8 }

        

        hwXQosVlanSlotStatOutBytes OBJECT-TYPE
            SYNTAX Counter64
            MAX-ACCESS read-only
            STATUS current
            DESCRIPTION
                "The byte number of transmittable packets."
            ::= { hwXQosVlanSlotStatEntry 9 }

        hwXQosVlanSlotStatOutBytesRate OBJECT-TYPE
            SYNTAX Counter64
            MAX-ACCESS read-only
            STATUS current
            DESCRIPTION
                "The rate number of transmittable packets by bytes."
            ::= { hwXQosVlanSlotStatEntry 10 }
     
 
--multicast        
        
        hwXQosVlanSlotStatInMcastPkts OBJECT-TYPE
            SYNTAX Counter64
            MAX-ACCESS read-only
            STATUS current
            DESCRIPTION
                "The number of received multicast packets."
            ::= { hwXQosVlanSlotStatEntry 11 }

        hwXQosVlanSlotStatInMcastPktsRate OBJECT-TYPE
            SYNTAX Counter64
            MAX-ACCESS read-only
            STATUS current
            DESCRIPTION
                "The rate of received multicast packets ."
            ::= { hwXQosVlanSlotStatEntry 12 }
        
        
        hwXQosVlanSlotStatInMcastBytes OBJECT-TYPE
            SYNTAX Counter64
            MAX-ACCESS read-only
            STATUS current
            DESCRIPTION
                "The number of received multicast packets' bytes."
            ::= { hwXQosVlanSlotStatEntry 13 }

        hwXQosVlanSlotStatInMcastBytesRate OBJECT-TYPE
            SYNTAX Counter64
            MAX-ACCESS read-only
            STATUS current
            DESCRIPTION
                "The rate of received multicast packets' bytes."
            ::= { hwXQosVlanSlotStatEntry 14 }
        
        
--broadcast        
        hwXQosVlanSlotStatInBcastPkts OBJECT-TYPE
            SYNTAX Counter64
            MAX-ACCESS read-only
            STATUS current
            DESCRIPTION
                "The number of received broadcast packets."
            ::= { hwXQosVlanSlotStatEntry 15 }

        hwXQosVlanSlotStatInBcastPktsRate OBJECT-TYPE
            SYNTAX Counter64
            MAX-ACCESS read-only
            STATUS current
            DESCRIPTION
                "The rate of received broadcast packets."
            ::= { hwXQosVlanSlotStatEntry 16 }        
        
        hwXQosVlanSlotStatInBcastBytes OBJECT-TYPE
            SYNTAX Counter64
            MAX-ACCESS read-only
            STATUS current
            DESCRIPTION
                "The number of received broadcast packets' bytes."
            ::= { hwXQosVlanSlotStatEntry 17 }

        hwXQosVlanSlotStatInBcastBytesRate OBJECT-TYPE
            SYNTAX Counter64
            MAX-ACCESS read-only
            STATUS current
            DESCRIPTION
                "The rate of received broadcast packets' bytes."
            ::= { hwXQosVlanSlotStatEntry 18 }
        
        
-- unknown-ucast        
        hwXQosVlanSlotStatInUnknownUcastPkts OBJECT-TYPE
            SYNTAX Counter64
            MAX-ACCESS read-only
            STATUS current
            DESCRIPTION
                "The number of received unknown broadcast packets."
            ::= { hwXQosVlanSlotStatEntry 19 }

        hwXQosVlanSlotStatInUnknownUcastPktsRate OBJECT-TYPE
            SYNTAX Counter64
            MAX-ACCESS read-only
            STATUS current
            DESCRIPTION
                "The rate of received unknown broadcast packets."
            ::= { hwXQosVlanSlotStatEntry 20 }
        
        
        hwXQosVlanSlotStatInUnknownUcastBytes OBJECT-TYPE
            SYNTAX Counter64
            MAX-ACCESS read-only
            STATUS current
            DESCRIPTION
                "The number of received unknown broadcast packets' bytes."
            ::= { hwXQosVlanSlotStatEntry 21 }

        hwXQosVlanSlotStatInUnknownUcastBytesRate OBJECT-TYPE
            SYNTAX Counter64
            MAX-ACCESS read-only
            STATUS current
            DESCRIPTION
                "The rate of received unknown broadcast packets' bytes."
            ::= { hwXQosVlanSlotStatEntry 22 }        
--drop    
        hwXQosVlanSlotStatInDropPkts OBJECT-TYPE
            SYNTAX Counter64
            MAX-ACCESS read-only
            STATUS current
            DESCRIPTION
                "The number of droped packets."
            ::= { hwXQosVlanSlotStatEntry 23 }   
        hwXQosVlanSlotStatInDropPktsRate OBJECT-TYPE
            SYNTAX Counter64
            MAX-ACCESS read-only
            STATUS current
            DESCRIPTION
                "The rate of droped packets."
            ::= { hwXQosVlanSlotStatEntry 24 }
        
        
        hwXQosVlanSlotStatInDropBytes OBJECT-TYPE
            SYNTAX Counter64
            MAX-ACCESS read-only
            STATUS current
            DESCRIPTION
                "The number of droped bytes."
            ::= { hwXQosVlanSlotStatEntry 25 }

        hwXQosVlanSlotStatInDropBytesRate OBJECT-TYPE
            SYNTAX Counter64
            MAX-ACCESS read-only
            STATUS current
            DESCRIPTION
                "The rate of droped bytes."
            ::= { hwXQosVlanSlotStatEntry 26 }   
                 
        hwXQosVlanSlotStatInDropPercentageBytesRate OBJECT-TYPE
            SYNTAX Counter64
            MAX-ACCESS read-only
            STATUS current
            DESCRIPTION
                "The rate of droped bytes."
            ::= { hwXQosVlanSlotStatEntry 27 }
 
-- buffer usage stat
    hwXQoSBufferUsageStatisticsObjects OBJECT IDENTIFIER ::= { hwXQoSStatisticsObjects 5 }

    --slot buffer usage
        hwXQoSBufferUsageSlotStatTable OBJECT-TYPE
            SYNTAX SEQUENCE OF HwXQoSBufferUsageSlotStatEntry
            MAX-ACCESS not-accessible
            STATUS current
            DESCRIPTION
                "The table contains statistics information for slot buffer usage."
            ::= { hwXQoSBufferUsageStatisticsObjects 1 }

        hwXQoSBufferUsageSlotStatEntry OBJECT-TYPE
            SYNTAX HwXQoSBufferUsageSlotStatEntry
            MAX-ACCESS not-accessible
            STATUS current
            DESCRIPTION
                "Entries of slot buffer usage statistics table."
            INDEX { hwXQosBufferUsageSlotStatFrameId, hwXQosBufferUsageSlotStatSlotId }
            ::= { hwXQoSBufferUsageSlotStatTable 1 }

        HwXQoSBufferUsageSlotStatEntry ::=
            SEQUENCE {
                hwXQosBufferUsageSlotStatFrameId
                    Integer32,
                hwXQosBufferUsageSlotStatSlotId
                    Integer32,
                hwXQosBufferUsageSlotStatTotalLength
                    Counter64,
                hwXQosBufferUsageSlotStatUsedLength
                    Counter64,
                hwXQosBufferUsageSlotStatRemainedLength
                    Counter64,
                hwXQosBufferUsageSlotStatPeakUsedLength
                    Counter64,
                hwXQosBufferUsageSlotStatAverageUsedLength
                    Counter64
             }

        hwXQosBufferUsageSlotStatFrameId OBJECT-TYPE
            SYNTAX Integer32
            MAX-ACCESS not-accessible
            STATUS current
            DESCRIPTION
                "The frame id of the device."
            ::= { hwXQoSBufferUsageSlotStatEntry 1 }

        hwXQosBufferUsageSlotStatSlotId OBJECT-TYPE
            SYNTAX Integer32
            MAX-ACCESS not-accessible
            STATUS current
            DESCRIPTION
                "The slot id of the device."
            ::= { hwXQoSBufferUsageSlotStatEntry 2 }
        
        hwXQosBufferUsageSlotStatTotalLength OBJECT-TYPE
            SYNTAX Counter64
            MAX-ACCESS read-only
            STATUS current
            DESCRIPTION
                "The total kbyte number of slot buffer."
            ::= { hwXQoSBufferUsageSlotStatEntry 3 }
        
        hwXQosBufferUsageSlotStatUsedLength OBJECT-TYPE
            SYNTAX Counter64
            MAX-ACCESS read-only
            STATUS current
            DESCRIPTION
                "The used kbyte number of slot buffer."
            ::= { hwXQoSBufferUsageSlotStatEntry 4 }
        
        hwXQosBufferUsageSlotStatRemainedLength OBJECT-TYPE
            SYNTAX Counter64
            MAX-ACCESS read-only
            STATUS current
            DESCRIPTION
                "The remained kbyte number of slot buffer."
            ::= { hwXQoSBufferUsageSlotStatEntry 5 }

        hwXQosBufferUsageSlotStatPeakUsedLength OBJECT-TYPE
            SYNTAX Counter64
            MAX-ACCESS read-only
            STATUS current
            DESCRIPTION
                "The used kbyte number of slot buffer."
            ::= { hwXQoSBufferUsageSlotStatEntry 6 }

       hwXQosBufferUsageSlotStatAverageUsedLength OBJECT-TYPE
            SYNTAX Counter64
            MAX-ACCESS read-only
            STATUS current
            DESCRIPTION
                "The used kbyte number of slot buffer."
            ::= { hwXQoSBufferUsageSlotStatEntry 7 }

    --interface buffer usage
        hwXQoSBufferUsageIfStatTable OBJECT-TYPE
            SYNTAX SEQUENCE OF HwXQoSBufferUsageIfStatEntry
            MAX-ACCESS not-accessible
            STATUS current
            DESCRIPTION
                "The table contains statistics information for interface buffer usage."
            ::= { hwXQoSBufferUsageStatisticsObjects 2 }

        hwXQoSBufferUsageIfStatEntry OBJECT-TYPE
            SYNTAX HwXQoSBufferUsageIfStatEntry
            MAX-ACCESS not-accessible
            STATUS current
            DESCRIPTION
                "Entries of interface buffer usage statistics table."
            INDEX { hwXQosBufferUsageIfStatIfindex }
            ::= { hwXQoSBufferUsageIfStatTable 1 }

        HwXQoSBufferUsageIfStatEntry ::=
            SEQUENCE {
                hwXQosBufferUsageIfStatIfindex
                    Integer32,
                hwXQosBufferUsageIfStatTotalLength
                    Counter64,
                hwXQosBufferUsageIfStatUsedLength
                    Counter64,
                hwXQosBufferUsageIfStatRemainedLength
                    Counter64,
                hwXQosBufferUsageIfStatPeakUsedLength
                    Counter64,
                hwXQosBufferUsageIfStatAverageUsedLength
                    Counter64
             }

        hwXQosBufferUsageIfStatIfindex OBJECT-TYPE
            SYNTAX Integer32
            MAX-ACCESS not-accessible
            STATUS current
            DESCRIPTION
                "The interface index."
            ::= { hwXQoSBufferUsageIfStatEntry 1 }

        hwXQosBufferUsageIfStatTotalLength OBJECT-TYPE
            SYNTAX Counter64
            MAX-ACCESS read-only
            STATUS current
            DESCRIPTION
                "The total kbyte number of interface buffer."
            ::= { hwXQoSBufferUsageIfStatEntry 2 }
        
        hwXQosBufferUsageIfStatUsedLength OBJECT-TYPE
            SYNTAX Counter64
            MAX-ACCESS read-only
            STATUS current
            DESCRIPTION
                "The used kbyte number of interface buffer."
            ::= { hwXQoSBufferUsageIfStatEntry 3 }

        hwXQosBufferUsageIfStatRemainedLength OBJECT-TYPE
            SYNTAX Counter64
            MAX-ACCESS read-only
            STATUS current
            DESCRIPTION
                "The remained kbyte number of interface buffer."
            ::= { hwXQoSBufferUsageIfStatEntry 4 }

        hwXQosBufferUsageIfStatPeakUsedLength OBJECT-TYPE
            SYNTAX Counter64
            MAX-ACCESS read-only
            STATUS current
            DESCRIPTION
                "The used kbyte number of interface buffer."
            ::= { hwXQoSBufferUsageIfStatEntry 5 }
			
        hwXQosBufferUsageIfStatAverageUsedLength OBJECT-TYPE
            SYNTAX Counter64
            MAX-ACCESS read-only
            STATUS current
            DESCRIPTION
                "The used kbyte number of interface buffer."
            ::= { hwXQoSBufferUsageIfStatEntry 6 }

    --interface queue buffer usage
        hwXQoSBufferUsageQueueStatTable OBJECT-TYPE
            SYNTAX SEQUENCE OF HwXQoSBufferUsageQueueStatEntry
            MAX-ACCESS not-accessible
            STATUS current
            DESCRIPTION
                "The table contains statistics information for interface queue buffer usage."
            ::= { hwXQoSBufferUsageStatisticsObjects 3 }

        hwXQoSBufferUsageQueueStatEntry OBJECT-TYPE
            SYNTAX HwXQoSBufferUsageQueueStatEntry
            MAX-ACCESS not-accessible
            STATUS current
            DESCRIPTION
                "Entries of interface queue buffer usage statistics table."
            INDEX { hwXQosBufferUsageQueueStatIfindex, hwXQosBufferUsageQueueStatQueueId }
            ::= { hwXQoSBufferUsageQueueStatTable 1 }

        HwXQoSBufferUsageQueueStatEntry ::=
            SEQUENCE {
                hwXQosBufferUsageQueueStatIfindex
                    Integer32,
                hwXQosBufferUsageQueueStatQueueId
                    Integer32,
                hwXQosBufferUsageQueueStatTotalLength
                    Counter64,
                hwXQosBufferUsageQueueStatUsedLength
                    Counter64,
                hwXQosBufferUsageQueueStatRemainedLength
                    Counter64,
                hwXQosBufferUsageQueueStatPeakUsedLength
                    Counter64,
                hwXQosBufferUsageQueueStatAverageUsedLength
                    Counter64
             }

        hwXQosBufferUsageQueueStatIfindex OBJECT-TYPE
            SYNTAX Integer32
            MAX-ACCESS not-accessible
            STATUS current
            DESCRIPTION
                "The interface index."
            ::= { hwXQoSBufferUsageQueueStatEntry 1 }

        hwXQosBufferUsageQueueStatQueueId OBJECT-TYPE
            SYNTAX Integer32 (0..7)
            MAX-ACCESS not-accessible
            STATUS current
            DESCRIPTION
                "The interface queue index.
                 The value ranges from 0 to 7. 
                "
            ::= { hwXQoSBufferUsageQueueStatEntry 2 }

        hwXQosBufferUsageQueueStatTotalLength OBJECT-TYPE
            SYNTAX Counter64
            MAX-ACCESS read-only
            STATUS current
            DESCRIPTION
                "The total kbyte number of interface queue buffer."
            ::= { hwXQoSBufferUsageQueueStatEntry 3 }
        
        hwXQosBufferUsageQueueStatUsedLength OBJECT-TYPE
            SYNTAX Counter64
            MAX-ACCESS read-only
            STATUS current
            DESCRIPTION
                "The used kbyte number of interface queue buffer."
            ::= { hwXQoSBufferUsageQueueStatEntry 4 }

        hwXQosBufferUsageQueueStatRemainedLength OBJECT-TYPE
            SYNTAX Counter64
            MAX-ACCESS read-only
            STATUS current
            DESCRIPTION
                "The remained kbyte number of interface queue buffer."
            ::= { hwXQoSBufferUsageQueueStatEntry 5 }

        hwXQosBufferUsageQueueStatPeakUsedLength OBJECT-TYPE
            SYNTAX Counter64
            MAX-ACCESS read-only
            STATUS current
            DESCRIPTION
                "The used kbyte number of interface queue buffer."
            ::= { hwXQoSBufferUsageQueueStatEntry 6 }
			
        hwXQosBufferUsageQueueStatAverageUsedLength OBJECT-TYPE
            SYNTAX Counter64
            MAX-ACCESS read-only
            STATUS current
            DESCRIPTION
                "The used kbyte number of interface queue buffer."
            ::= { hwXQoSBufferUsageQueueStatEntry 7 }

    -- 1.3.6.1.4.1.2011.5.25.32.4.1.5
    hwXQoSGlobalObjects OBJECT IDENTIFIER ::= { hwXQoSObjects 5 }
    
    -- 1.3.6.1.4.1.2011.5.25.32.4.1.5.1
    hwXQoSSoftCarCfgTable OBJECT-TYPE
        SYNTAX SEQUENCE OF HwXQoSSoftCarCfgEntry
        MAX-ACCESS not-accessible
        STATUS current
        DESCRIPTION
            "A table of software CAR  configuration information."
        ::= { hwXQoSGlobalObjects 1 }
    
    -- 1.3.6.1.4.1.2011.5.25.32.4.1.5.1.1
    hwXQoSSoftCarCfgEntry OBJECT-TYPE
        SYNTAX HwXQoSSoftCarCfgEntry
        MAX-ACCESS not-accessible
        STATUS current
        DESCRIPTION
            "Software CAR configuration information entry."
        INDEX { hwXQoSSoftCarIndex }
        ::= { hwXQoSSoftCarCfgTable 1 }
    
    HwXQoSSoftCarCfgEntry ::=
        SEQUENCE { 
            hwXQoSSoftCarIndex
                Integer32,
            hwXQoSSoftCarName
                OCTET STRING,
            hwXQoSSoftCarCir
                Integer32,
            hwXQoSSoftCarCbs
                Integer32,
            hwXQoSSoftCarRowStatus
                RowStatus
         }

    -- 1.3.6.1.4.1.2011.5.25.32.4.1.5.1.1.1
    hwXQoSSoftCarIndex OBJECT-TYPE
        SYNTAX Integer32 (0..65534)
        MAX-ACCESS not-accessible
        STATUS current
        DESCRIPTION
            "Index of software car."
        ::= { hwXQoSSoftCarCfgEntry 1 }
    
    -- 1.3.6.1.4.1.2011.5.25.32.4.1.5.1.1.2
    hwXQoSSoftCarName OBJECT-TYPE
        SYNTAX OCTET STRING (SIZE (1..31))
        MAX-ACCESS read-create
        STATUS current
        DESCRIPTION
            "Software car name."
        ::= { hwXQoSSoftCarCfgEntry 2 }
    
    -- 1.3.6.1.4.1.2011.5.25.32.4.1.5.1.1.3
    hwXQoSSoftCarCir OBJECT-TYPE
        SYNTAX Integer32
        MAX-ACCESS read-create
        STATUS current
        DESCRIPTION
            "Committed Information Rate. Unit: kbps."
        ::= { hwXQoSSoftCarCfgEntry 3 }
    
    -- 1.3.6.1.4.1.2011.5.25.32.4.1.5.1.1.4
    hwXQoSSoftCarCbs OBJECT-TYPE
        SYNTAX Integer32
        MAX-ACCESS read-create
        STATUS current
        DESCRIPTION
            "Committed Burst Size. Unit: byte"
        ::= { hwXQoSSoftCarCfgEntry 4 }
    
    -- 1.3.6.1.4.1.2011.5.25.32.4.1.5.1.1.5
    hwXQoSSoftCarRowStatus OBJECT-TYPE
        SYNTAX RowStatus
        MAX-ACCESS read-create
        STATUS current
        DESCRIPTION
            "RowStatus. Three actions are used: active,
            createAndGo, destroy."
        ::= { hwXQoSSoftCarCfgEntry 5 }
    
    -- 1.3.6.1.4.1.2011.5.25.32.4.1.5.2
    hwXQoSGlobalWredClassCfgTable OBJECT-TYPE
        SYNTAX SEQUENCE OF HwXQoSGlobalWredClassCfgEntry
        MAX-ACCESS not-accessible
        STATUS current
        DESCRIPTION
            "A table of class based Wred  configuration information."
        ::= { hwXQoSGlobalObjects 2 }
    
    -- 1.3.6.1.4.1.2011.5.25.32.4.1.5.2.1
    hwXQoSGlobalWredClassCfgEntry OBJECT-TYPE
        SYNTAX HwXQoSGlobalWredClassCfgEntry
        MAX-ACCESS not-accessible
        STATUS current
        DESCRIPTION
            "Class based Wred configuration information entry."
        INDEX { hwXQoSGlobalWredClassIndex }
        ::= { hwXQoSGlobalWredClassCfgTable 1 }
    
    HwXQoSGlobalWredClassCfgEntry ::=
        SEQUENCE { 
            hwXQoSGlobalWredClassIndex
                Integer32,
            hwXQoSGlobalWredClassLowlimit
                Integer32,
            hwXQoSGlobalWredClassHighlimit
                Integer32,
            hwXQoSGlobalWredClassDiscardProbability
                Integer32,
            hwXQoSGlobalWredClassSetDefault
                Integer32
         }

    -- 1.3.6.1.4.1.2011.5.25.32.4.1.5.2.1.1
    hwXQoSGlobalWredClassIndex OBJECT-TYPE
        SYNTAX Integer32 (0..7)
        MAX-ACCESS not-accessible
        STATUS current
        DESCRIPTION
            "Index of wred class."
        ::= { hwXQoSGlobalWredClassCfgEntry 1 }
    
    -- 1.3.6.1.4.1.2011.5.25.32.4.1.5.2.1.2
    hwXQoSGlobalWredClassLowlimit OBJECT-TYPE
        SYNTAX Integer32
        MAX-ACCESS read-write
        STATUS current
        DESCRIPTION
            "The Wred Lowlimit."
        ::= { hwXQoSGlobalWredClassCfgEntry 2 }
    
    -- 1.3.6.1.4.1.2011.5.25.32.4.1.5.2.1.3
    hwXQoSGlobalWredClassHighlimit OBJECT-TYPE
        SYNTAX Integer32
        MAX-ACCESS read-write
        STATUS current
        DESCRIPTION
            "The Wred Highlimit."
        ::= { hwXQoSGlobalWredClassCfgEntry 3 }
    
    -- 1.3.6.1.4.1.2011.5.25.32.4.1.5.2.1.4
    hwXQoSGlobalWredClassDiscardProbability OBJECT-TYPE
        SYNTAX Integer32
        MAX-ACCESS read-write
        STATUS current
        DESCRIPTION
            "The Wred Discard Probability."
        ::= { hwXQoSGlobalWredClassCfgEntry 4 }
    
    -- 1.3.6.1.4.1.2011.5.25.32.4.1.5.2.1.5
    hwXQoSGlobalWredClassSetDefault OBJECT-TYPE
        SYNTAX Integer32 (0..1)
        MAX-ACCESS read-write
        STATUS current
        DESCRIPTION
            "This OID is used for setting the WRED class info to default.
            When you want to set the value to default, set this OID to 1.
            "
        ::= { hwXQoSGlobalWredClassCfgEntry 5 }
    
    -- 1.3.6.1.4.1.2011.5.25.32.4.1.5.3
    hwXQoSGlobalWredTypeCfgTable OBJECT-TYPE
        SYNTAX SEQUENCE OF HwXQoSGlobalWredTypeCfgEntry
        MAX-ACCESS not-accessible
        STATUS current
        DESCRIPTION
            "A table of type based Wred  configuration information."
        ::= { hwXQoSGlobalObjects 3 }
    
    -- 1.3.6.1.4.1.2011.5.25.32.4.1.5.3.1
    hwXQoSGlobalWredTypeCfgEntry OBJECT-TYPE
        SYNTAX HwXQoSGlobalWredTypeCfgEntry
        MAX-ACCESS not-accessible
        STATUS current
        DESCRIPTION
            "Type based Wred  configuration information entry."
        INDEX { hwXQoSGlobalWredTypeIndex }
        ::= { hwXQoSGlobalWredTypeCfgTable 1 }
    
    HwXQoSGlobalWredTypeCfgEntry ::=
        SEQUENCE { 
            hwXQoSGlobalWredTypeIndex
                Integer32,
            hwXQoSGlobalWredTypeName
                OCTET STRING,
            hwXQoSGlobalWredTypeLowlimit
                Integer32,
            hwXQoSGlobalWredTypeHighlimit
                Integer32,
            hwXQoSGlobalWredTypeDiscardProbability
                Integer32,
            hwXQoSGlobalWredTypeSetDefault
                Integer32
         }

    -- 1.3.6.1.4.1.2011.5.25.32.4.1.5.3.1.1
    hwXQoSGlobalWredTypeIndex OBJECT-TYPE
        SYNTAX Integer32 (0..3)
        MAX-ACCESS not-accessible
        STATUS current
        DESCRIPTION
            "Index of type."
        ::= { hwXQoSGlobalWredTypeCfgEntry 1 }
    
    -- 1.3.6.1.4.1.2011.5.25.32.4.1.5.3.1.2
    hwXQoSGlobalWredTypeName OBJECT-TYPE
        SYNTAX OCTET STRING (SIZE (1..31))
        MAX-ACCESS read-only
        STATUS current
        DESCRIPTION
            "Name of type."
        ::= { hwXQoSGlobalWredTypeCfgEntry 2 }
        
    -- 1.3.6.1.4.1.2011.5.25.32.4.1.5.3.1.3
    hwXQoSGlobalWredTypeLowlimit OBJECT-TYPE
        SYNTAX Integer32
        MAX-ACCESS read-write
        STATUS current
        DESCRIPTION
            "The Wred Lowlimit."
        ::= { hwXQoSGlobalWredTypeCfgEntry 3 }
    
    -- 1.3.6.1.4.1.2011.5.25.32.4.1.5.3.1.4
    hwXQoSGlobalWredTypeHighlimit OBJECT-TYPE
        SYNTAX Integer32
        MAX-ACCESS read-write
        STATUS current
        DESCRIPTION
            "The Wred Highlimit."
        ::= { hwXQoSGlobalWredTypeCfgEntry 4 }
    
    -- 1.3.6.1.4.1.2011.5.25.32.4.1.5.3.1.5
    hwXQoSGlobalWredTypeDiscardProbability OBJECT-TYPE
        SYNTAX Integer32
        MAX-ACCESS read-write
        STATUS current
        DESCRIPTION
            "The Wred Discard Probability."
        ::= { hwXQoSGlobalWredTypeCfgEntry 5 }
    
    -- 1.3.6.1.4.1.2011.5.25.32.4.1.5.3.1.6
    hwXQoSGlobalWredTypeSetDefault OBJECT-TYPE
        SYNTAX Integer32 (0..1)
        MAX-ACCESS read-write
        STATUS current
        DESCRIPTION
            "This OID is used for setting the WRED type info to default.
            When you want to set the value to default, set this OID to 1."
        ::= { hwXQoSGlobalWredTypeCfgEntry 6 }

        
    hwXQoSVlanBcastSuppressTable OBJECT-TYPE
        SYNTAX SEQUENCE OF HwXQoSVlanBcastSuppressEntry
        MAX-ACCESS not-accessible
        STATUS current
        DESCRIPTION
            "A table of VLAN broadcast suppression."
        ::= { hwXQoSGlobalObjects 4 }

    
    hwXQoSVlanBcastSuppressEntry OBJECT-TYPE
        SYNTAX HwXQoSVlanBcastSuppressEntry
        MAX-ACCESS not-accessible
        STATUS current
        DESCRIPTION
            "The entry of VLAN broadcast suppression."
        INDEX { hwXQoSVlanBcastSuppressVlanId }
        ::= { hwXQoSVlanBcastSuppressTable 1 }

    
    HwXQoSVlanBcastSuppressEntry ::=
        SEQUENCE { 
            hwXQoSVlanBcastSuppressVlanId
                Integer32,
            hwXQoSVlanBcastSuppressValue
                Integer32,
            hwXQoSVlanBcastSuppressRowStatus
                RowStatus
         }

    hwXQoSVlanBcastSuppressVlanId OBJECT-TYPE
        SYNTAX Integer32 (1..4094)
        MAX-ACCESS not-accessible
        STATUS current
        DESCRIPTION
            "VLAN ID."
        ::= { hwXQoSVlanBcastSuppressEntry 1 }

    
    hwXQoSVlanBcastSuppressValue OBJECT-TYPE
        SYNTAX Integer32 (64..1000000)
        MAX-ACCESS read-create
        STATUS current
        DESCRIPTION
            "Suppression value for VLAN, unit KBPS."
        ::= { hwXQoSVlanBcastSuppressEntry 2 }

    
    hwXQoSVlanBcastSuppressRowStatus OBJECT-TYPE
        SYNTAX RowStatus
        MAX-ACCESS read-create
        STATUS current
        DESCRIPTION
            "Row status. Two actions are used: createAndGo, destroy"
        ::= { hwXQoSVlanBcastSuppressEntry 3 }
     hwXQoSScheduleProfileTable OBJECT-TYPE
        SYNTAX SEQUENCE OF HwXQoSScheduleProfileEntry
        MAX-ACCESS not-accessible
        STATUS current
        DESCRIPTION
            "A table of schedule profile."
        ::= { hwXQoSGlobalObjects 5 }

    
    hwXQoSScheduleProfileEntry OBJECT-TYPE
        SYNTAX HwXQoSScheduleProfileEntry
        MAX-ACCESS not-accessible
        STATUS current
        DESCRIPTION
            "The entry of schedule profile."
        INDEX { hwXQoSScheduleProfileName }
        ::= { hwXQoSScheduleProfileTable 1 }

    
    HwXQoSScheduleProfileEntry ::=
        SEQUENCE { 
            hwXQoSScheduleProfileName
                OCTET STRING,     
            hwXQoSScheduleQueueMode  
                INTEGER,      
            hwXQoSScheduleQueueBeWeight
                Integer32,   
            hwXQoSScheduleQueueAf1Weight
                Integer32, 
            hwXQoSScheduleQueueAf2Weight
                Integer32, 
            hwXQoSScheduleQueueAf3Weight
                Integer32, 
            hwXQoSScheduleQueueAf4Weight
                Integer32, 
            hwXQoSScheduleQueueCs6Weight
                Integer32,  
            hwXQoSScheduleQueueCs7Weight
                Integer32, 
            hwXQoSScheduleQueueEfWeight
                Integer32, 
            hwXQoSScheduleProfileRowStatus
                RowStatus
         }
    
    hwXQoSScheduleProfileName OBJECT-TYPE
            SYNTAX OCTET STRING (SIZE (1..31))
            MAX-ACCESS not-accessible
            STATUS current
            DESCRIPTION
                "The object specifies the schedule profile name."
            ::= { hwXQoSScheduleProfileEntry 1 }
    
    hwXQoSScheduleQueueMode OBJECT-TYPE
        SYNTAX INTEGER {
            pq(1), 
            wrr(3),
            wfq(4),
            default(5),
            drr(6)
           }
        MAX-ACCESS read-write
        STATUS current
        DESCRIPTION
            "The Queue mode:       
            pq(1), 
            wrr(3),
            wfq(4),
            default(5),
            drr(6)
            "
        ::= { hwXQoSScheduleProfileEntry 2 }

    hwXQoSScheduleQueueBeWeight OBJECT-TYPE
        SYNTAX Integer32
        MAX-ACCESS read-write
        STATUS current
        DESCRIPTION
            "The be queue weight value when in wrr or drr queue mode."
        ::= { hwXQoSScheduleProfileEntry 3 } 
        
    hwXQoSScheduleQueueAf1Weight OBJECT-TYPE
        SYNTAX Integer32
        MAX-ACCESS read-write
        STATUS current
        DESCRIPTION
            "The af1 queue weight value when in wrr or drr queue mode."
         ::= { hwXQoSScheduleProfileEntry 4 } 

    hwXQoSScheduleQueueAf2Weight OBJECT-TYPE
        SYNTAX Integer32
        MAX-ACCESS read-write
        STATUS current
        DESCRIPTION
            "The af2 queue weight value when in wrr or drr queue mode."
        ::= { hwXQoSScheduleProfileEntry 5 } 
    
    hwXQoSScheduleQueueAf3Weight OBJECT-TYPE
        SYNTAX Integer32
        MAX-ACCESS read-write
        STATUS current
        DESCRIPTION
            "The af3 queue weight value when in wrr or drr queue mode."
        ::= { hwXQoSScheduleProfileEntry 6 }
    
     hwXQoSScheduleQueueAf4Weight OBJECT-TYPE
        SYNTAX Integer32
        MAX-ACCESS read-write
        STATUS current
        DESCRIPTION
            "The af4 queue weight value when in wrr or drr queue mode."
        ::= { hwXQoSScheduleProfileEntry 7 }
       
    hwXQoSScheduleQueueCs6Weight OBJECT-TYPE
        SYNTAX Integer32
        MAX-ACCESS read-write
        STATUS current
        DESCRIPTION
            "The cs6 queue weight value when in wrr or drr queue mode."
        ::= { hwXQoSScheduleProfileEntry 8 }
   
     hwXQoSScheduleQueueCs7Weight OBJECT-TYPE
        SYNTAX Integer32
        MAX-ACCESS read-write
        STATUS current
        DESCRIPTION
            "The cs7 queue weight value when in wrr or drr queue mode."
        ::= { hwXQoSScheduleProfileEntry 9 }
    
     hwXQoSScheduleQueueEfWeight OBJECT-TYPE
        SYNTAX Integer32
        MAX-ACCESS read-write
        STATUS current
        DESCRIPTION
            "The ef queue weight value when in wrr or drr queue mode."
        ::= { hwXQoSScheduleProfileEntry 10 }

    hwXQoSScheduleProfileRowStatus OBJECT-TYPE
        SYNTAX RowStatus
        MAX-ACCESS read-create
        STATUS current
        DESCRIPTION
            "Row status. Two actions are used: createAndGo, destroy"
        ::= { hwXQoSScheduleProfileEntry 51 }
  
 -- ******************************************************************
-- BEGIN: Added by w00218179, 2013/6/13           
--     ******************************************************************
-- 
-- hwXQosCarResourceTable
-- 
-- ******************************************************************
    -- 1.3.6.1.4.1.2011.5.25.32.4.1.5.6
	hwXQosCarResourceTable OBJECT-TYPE
		SYNTAX SEQUENCE OF HwXQosCarResourceEntry
		MAX-ACCESS not-accessible
		STATUS current
		DESCRIPTION
			"hwXQosCarResourceTable "
		::= { hwXQoSGlobalObjects 6 }      
        
    -- 1.3.6.1.4.1.2011.5.25.32.4.1.5.6.1
	hwXQosCarResourceEntry OBJECT-TYPE
		SYNTAX HwXQosCarResourceEntry
		MAX-ACCESS not-accessible
		STATUS current
		DESCRIPTION
			"hwXQosCarResourceEntry "
			INDEX { hwXQosCarResourceDirection, hwXQosCarResourceSlotNumber,hwXQosCarResourceServiceType}
		::= { hwXQosCarResourceTable 1 }
        
	HwXQosCarResourceEntry ::=
	    SEQUENCE {                        
	        hwXQosCarResourceDirection
	            INTEGER,
	        hwXQosCarResourceSlotNumber
	            Integer32, 
	        hwXQosCarResourceServiceType
	            INTEGER,
	        hwXQosCarResourceTotalValue
	            Integer32,   
	        hwXQosCarResourceAllocatedValue
	            Integer32,
	        hwXQosCarResourceFreeValue
	            Integer32	            
        } 
             
    -- 1.3.6.1.4.1.2011.5.25.32.4.1.5.6.1.1
	hwXQosCarResourceDirection OBJECT-TYPE
	    SYNTAX INTEGER
	        {
	        inbound(1),
	        outbound(2)
	        }
	    MAX-ACCESS read-only
	    STATUS current
	    DESCRIPTION
	        "The value of this object identifies the number of car resource on which direction."
	    ::= { hwXQosCarResourceEntry 1 } 
	    
    -- 1.3.6.1.4.1.2011.5.25.32.4.1.5.6.1.2
	hwXQosCarResourceSlotNumber OBJECT-TYPE
		SYNTAX Integer32 (0..128)
		MAX-ACCESS read-only
		STATUS current
		DESCRIPTION
		   "The value of this object identifies the number of car resource on which slot "
		::= { hwXQosCarResourceEntry 2 }  
		
    -- 1.3.6.1.4.1.2011.5.25.32.4.1.5.6.1.3
	hwXQosCarResourceServiceType OBJECT-TYPE
		SYNTAX INTEGER 
		{     
		    acl(1),
		    interface(2),
		    family(3),
		    user(4),
		    daa(5),
		    suppress(6)       
		}
		MAX-ACCESS read-only
		STATUS current
		DESCRIPTION
		   "Service type:
		    ACL      (1),
		    INTERFACE(2),
		    FAMILY   (3),
		    USER     (4),
		    DAA      (5),
		    SUPPRESS (6)"
		::= { hwXQosCarResourceEntry 3 }
        
    -- 1.3.6.1.4.1.2011.5.25.32.4.1.5.6.1.4
	hwXQosCarResourceTotalValue OBJECT-TYPE
	    SYNTAX Integer32 (0..2147483647)
	    MAX-ACCESS read-only
	    STATUS current
	    DESCRIPTION
	        "The number of the total car resource"
	    ::= { hwXQosCarResourceEntry 4 }   
	    
    -- 1.3.6.1.4.1.2011.5.25.32.4.1.5.6.1.5
	hwXQosCarResourceAllocatedValue OBJECT-TYPE
		SYNTAX Integer32 (0..2147483647)
		MAX-ACCESS read-only
		STATUS current
		DESCRIPTION
		   "The number of the used car resource "
		::= { hwXQosCarResourceEntry 5 }
		
    -- 1.3.6.1.4.1.2011.5.25.32.4.1.5.6.1.6
	hwXQosCarResourceFreeValue OBJECT-TYPE
		SYNTAX Integer32 (0..2147483647)
		MAX-ACCESS read-only
		STATUS current
		DESCRIPTION
		   "The number of the free car resource "
		::= { hwXQosCarResourceEntry 6 }
            
-- END: Added by w00218179, 2013/6/13      
 
  -- defend statistics
        hwXQoSCpDefendObjects OBJECT IDENTIFIER ::= { hwXQoSObjects 6 }

        hwXQoSCpDefendStatisticsTable OBJECT-TYPE
            SYNTAX SEQUENCE OF HwXQoSCpDefendStatisticsEntry
            MAX-ACCESS not-accessible
            STATUS current
            DESCRIPTION
                "A table of statistics on attack defense"
            ::= { hwXQoSCpDefendObjects 1 }

        hwXQoSCpDefendStatisticsEntry OBJECT-TYPE
            SYNTAX HwXQoSCpDefendStatisticsEntry
            MAX-ACCESS not-accessible
            STATUS current
            DESCRIPTION
                "A table of statistics information on attack defense"
            INDEX { hwXQoSCpDefendChassisID, hwXQoSCpDefendSlotId, hwXQoSCpDefendObjectIndex }
            ::= { hwXQoSCpDefendStatisticsTable 1 }

        HwXQoSCpDefendStatisticsEntry ::=
            SEQUENCE { 
                hwXQoSCpDefendSlotId
                    Integer32,
                hwXQoSCpDefendObjectIndex
                    Integer32,
                hwXQoSCpDefendPassedPackets
                    Counter64,
                hwXQoSCpDefendPassedBytes
                    Counter64,
                hwXQoSCpDefendPassedPacketRate
                    Counter64,
                hwXQoSCpDefendPassedByteRate
                    Counter64,
                hwXQoSCpDefendDiscardedPackets
                    Counter64,
                hwXQoSCpDefendDiscardedBytes
                    Counter64,
                hwXQoSCpDefendDiscardedPacketRate
                    Counter64,
                hwXQoSCpDefendDiscardedByteRate
                    Counter64,
                hwXQoSCpDefendDiscardedThreshold
                    Counter32,
                hwXQoSCpDefendChassisID
                    Integer32                    
             }

        hwXQoSCpDefendSlotId OBJECT-TYPE
            SYNTAX Integer32 (1..32)
            MAX-ACCESS read-only
            STATUS current
            DESCRIPTION
                "Slot number of statistics for attack defense."
            ::= { hwXQoSCpDefendStatisticsEntry 1 }

        hwXQoSCpDefendObjectIndex OBJECT-TYPE
            SYNTAX Integer32 (0..511)
            MAX-ACCESS read-only
            STATUS current
            DESCRIPTION
                "Index of attack defense object."
            ::= { hwXQoSCpDefendStatisticsEntry 2 }

        hwXQoSCpDefendPassedPackets OBJECT-TYPE
            SYNTAX Counter64
            MAX-ACCESS read-only
            STATUS current
            DESCRIPTION
                "Number of packets passed the attack defense."
            ::= { hwXQoSCpDefendStatisticsEntry 11 }

        hwXQoSCpDefendPassedBytes OBJECT-TYPE
            SYNTAX Counter64
            MAX-ACCESS read-only
            STATUS current
            DESCRIPTION
                "Number of bytes passed the attack defense."
            ::= { hwXQoSCpDefendStatisticsEntry 12 }

        hwXQoSCpDefendPassedPacketRate OBJECT-TYPE
            SYNTAX Counter64
            MAX-ACCESS read-only
            STATUS current
            DESCRIPTION
                "Rate of packets passed the attack defense. Unit: pps"
            ::= { hwXQoSCpDefendStatisticsEntry 13 }

        hwXQoSCpDefendPassedByteRate OBJECT-TYPE
            SYNTAX Counter64
            MAX-ACCESS read-only
            STATUS current
            DESCRIPTION
                "Rate of bytes passed the attack defense. Unit: bps"
            ::= { hwXQoSCpDefendStatisticsEntry 14 }
            
        hwXQoSCpDefendDiscardedPackets OBJECT-TYPE
            SYNTAX Counter64
            MAX-ACCESS read-only
            STATUS current
            DESCRIPTION
                "Number of packets discarded in the attack defense."
            ::= { hwXQoSCpDefendStatisticsEntry 15 }

        hwXQoSCpDefendDiscardedBytes OBJECT-TYPE
            SYNTAX Counter64
            MAX-ACCESS read-only
            STATUS current
            DESCRIPTION
                "Number of bytes discarded in the attack defense."
            ::= { hwXQoSCpDefendStatisticsEntry 16 }

        hwXQoSCpDefendDiscardedPacketRate OBJECT-TYPE
            SYNTAX Counter64
            MAX-ACCESS read-only
            STATUS current
            DESCRIPTION
                "Rate of packets discarded in the attack defense. Unit: pps"
            ::= { hwXQoSCpDefendStatisticsEntry 17 }

        hwXQoSCpDefendDiscardedByteRate OBJECT-TYPE
            SYNTAX Counter64
            MAX-ACCESS read-only
            STATUS current
            DESCRIPTION
                "Rate of bytes discarded in the attack defense. Unit: bps"
            ::= { hwXQoSCpDefendStatisticsEntry 18 }

        hwXQoSCpDefendDiscardedThreshold OBJECT-TYPE
            SYNTAX Counter32
            MAX-ACCESS read-only
            STATUS current
            DESCRIPTION
                "Discarded packets threshold of alarm. Unit: packets"
            ::= { hwXQoSCpDefendStatisticsEntry 19 }
            
        hwXQoSCpDefendChassisID OBJECT-TYPE
            SYNTAX Integer32 (1..32)
            MAX-ACCESS read-only
            STATUS current
            DESCRIPTION
                "Chassis number of statistics for attack defense."
            ::= { hwXQoSCpDefendStatisticsEntry 20 }

-- Urpf discard statistics
        hwXQoSUrpfObjects OBJECT IDENTIFIER ::= { hwXQoSObjects 7 }

        hwXQoSUrpfDiscardStatisticsTable OBJECT-TYPE
            SYNTAX SEQUENCE OF HwXQoSUrpfDiscardStatisticsEntry
            MAX-ACCESS not-accessible
            STATUS current
            DESCRIPTION
                "A table of statistics on discarded packets for IP URPF"
            ::= { hwXQoSUrpfObjects 1 }

        hwXQoSUrpfDiscardStatisticsEntry OBJECT-TYPE
            SYNTAX HwXQoSUrpfDiscardStatisticsEntry
            MAX-ACCESS not-accessible
            STATUS current
            DESCRIPTION
                "Urpf discard statistics entry"
            INDEX { hwXQoSUrpfSlotPhysicalIndex }
            ::= { hwXQoSUrpfDiscardStatisticsTable 1 }

        HwXQoSUrpfDiscardStatisticsEntry ::=
            SEQUENCE { 
                hwXQoSUrpfSlotPhysicalIndex
                    Integer32,
                hwXQoSUrpfDiscardedPackets
                    Counter64
                  }

        hwXQoSUrpfSlotPhysicalIndex OBJECT-TYPE
            SYNTAX Integer32
            MAX-ACCESS not-accessible
            STATUS current
            DESCRIPTION
                "The index of hwXQoSUrpfDiscardStatisticsTable.This index is identical to entPhysicalIndex in ENTITY-MIB."
            ::= { hwXQoSUrpfDiscardStatisticsEntry 1 }
                
        hwXQoSUrpfDiscardedPackets OBJECT-TYPE
            SYNTAX Counter64
            MAX-ACCESS read-only
            STATUS current
            DESCRIPTION
                "Number of packets discarded."
            ::= { hwXQoSUrpfDiscardStatisticsEntry 2 }


        hwXQoSVlanCfgObjects OBJECT IDENTIFIER ::= { hwXQoSObjects 8 }

        
        hwXQoSVlanCfgTable OBJECT-TYPE
            SYNTAX SEQUENCE OF HwXQoSVlanCfgEntry
            MAX-ACCESS not-accessible
            STATUS current
            DESCRIPTION
                "The table of vlan config information."
            ::= { hwXQoSVlanCfgObjects 1 }

        
        hwXQoSVlanCfgEntry OBJECT-TYPE
            SYNTAX HwXQoSVlanCfgEntry
            MAX-ACCESS not-accessible
            STATUS current
            DESCRIPTION
                "Vlan config information entry."
            INDEX { hwXQosVlanStatVlanId }
            ::= { hwXQoSVlanCfgTable 1 }

        
        HwXQoSVlanCfgEntry ::=
            SEQUENCE { 
                hwXQoSVlanStatEnable
                    EnabledStatus
             }

        hwXQoSVlanStatEnable OBJECT-TYPE
            SYNTAX EnabledStatus
            MAX-ACCESS read-write
            STATUS current
            DESCRIPTION
                "Vlan statistics enable: enable(1),disable(2)."
            ::= { hwXQoSVlanCfgEntry 1 }
        
    -- Redirect multi-ip
        hwXQoSRedirectNextHopObjects OBJECT IDENTIFIER ::= { hwXQoSObjects 9 }

        hwXQoSRedirectNextHopTable OBJECT-TYPE
            SYNTAX SEQUENCE OF HwXQoSRedirectNextHopEntry
            MAX-ACCESS not-accessible
            STATUS current
            DESCRIPTION
                "A table of the redirect next hop"
            ::= { hwXQoSRedirectNextHopObjects 1 }

        hwXQoSRedirectNextHopEntry OBJECT-TYPE
            SYNTAX HwXQoSRedirectNextHopEntry
            MAX-ACCESS not-accessible
            STATUS current
            DESCRIPTION
                "A table of the redirect next hop information"
            INDEX { hwXQoSRedirectNextHopBehaviorName }
            ::= { hwXQoSRedirectNextHopTable 1 }

        HwXQoSRedirectNextHopEntry ::=
            SEQUENCE { 
                hwXQoSRedirectNextHopBehaviorName
                    OCTET STRING,
                hwXQoSRedirectNextHopOldIp
                    IpAddress,
                hwXQoSRedirectNextHopNewIp
                    IpAddress
             }  

        hwXQoSRedirectNextHopBehaviorName OBJECT-TYPE
            SYNTAX OCTET STRING (SIZE (1..32))
            MAX-ACCESS read-only
            STATUS current
            DESCRIPTION
                "Traffic behavior name."
            ::= { hwXQoSRedirectNextHopEntry 1 }
            
        hwXQoSRedirectNextHopOldIp OBJECT-TYPE
            SYNTAX IpAddress
            MAX-ACCESS read-only
            STATUS current
            DESCRIPTION
                "The redirect next hop."
            ::= { hwXQoSRedirectNextHopEntry 2 } 
             
        hwXQoSRedirectNextHopNewIp OBJECT-TYPE
            SYNTAX IpAddress
            MAX-ACCESS read-only
            STATUS current
            DESCRIPTION
                "The redirect next hop."
            ::= { hwXQoSRedirectNextHopEntry 3 }


-- irsm

       hwXQoSIrsmObjects OBJECT IDENTIFIER ::= { hwXQoSObjects 10 }  
        
         hwXQoSIrsmTable OBJECT-TYPE
            SYNTAX SEQUENCE OF HwXQoSIrsmEntry
            MAX-ACCESS not-accessible
            STATUS current
            DESCRIPTION
              "A table of Irsm "
            ::= { hwXQoSIrsmObjects 1 }

       hwXQoSIrsmEntry OBJECT-TYPE
            SYNTAX HwXQoSIrsmEntry
            MAX-ACCESS not-accessible
            STATUS current
            DESCRIPTION
             "A table of Irsm"
            INDEX { hwXQoSIrsmSourceAddress}
            ::= { hwXQoSIrsmTable 1 }

       HwXQoSIrsmEntry ::=
            SEQUENCE { 
                hwXQoSIrsmSourceAddress
                    IpAddress,
                hwXQoSIrsmGroupAddress
                    IpAddress,
                hwXQoSIrsmTime
                    TimeTicks,
                hwXQoSIrsmDelay
                    Integer32,
                hwXQoSIrsmThreshold
                    Integer32,
                hwXQoSIrsmUpstream
                    IpAddress,
                hwXQoSIrsmLocal
                    IpAddress,
                hwXQoSIrsmTotalPacket
                    Integer32,
                hwXQoSIrsmDropPacket
                    Integer32
            }

       hwXQoSIrsmSourceAddress OBJECT-TYPE
            SYNTAX IpAddress
            MAX-ACCESS read-only
            STATUS current
            DESCRIPTION
               "hwXQoSIrsmSourceAddress "
            ::= { hwXQoSIrsmEntry 1 }    

       hwXQoSIrsmGroupAddress OBJECT-TYPE
            SYNTAX IpAddress
            MAX-ACCESS read-only
            STATUS current
            DESCRIPTION
              "hwXQoSIrsmGroupAddress "
            ::= { hwXQoSIrsmEntry 2 }

      hwXQoSIrsmTime OBJECT-TYPE
            SYNTAX TimeTicks
            MAX-ACCESS read-only
            STATUS current
            DESCRIPTION
              "hwXQoSIrsmTime "
            ::= { hwXQoSIrsmEntry 3 }

     hwXQoSIrsmDelay OBJECT-TYPE
            SYNTAX Integer32
            MAX-ACCESS read-only
            STATUS current
            DESCRIPTION
              "hwXQoSIrsmDelay "
            ::= { hwXQoSIrsmEntry 4 }

     hwXQoSIrsmThreshold OBJECT-TYPE
            SYNTAX Integer32
            MAX-ACCESS read-only
            STATUS current
            DESCRIPTION
              "hwXQoSIrsmThreshold "
            ::= { hwXQoSIrsmEntry 5 }
              
     hwXQoSIrsmUpstream OBJECT-TYPE
            SYNTAX IpAddress
            MAX-ACCESS read-only
            STATUS current
            DESCRIPTION
              "hwXQoSIrsmUpstream "
            ::= { hwXQoSIrsmEntry 6 }

      hwXQoSIrsmLocal OBJECT-TYPE
            SYNTAX IpAddress
            MAX-ACCESS read-only
            STATUS current
            DESCRIPTION
               "hwXQoSIrsmLocal "
            ::= { hwXQoSIrsmEntry 7 }

      hwXQoSIrsmTotalPacket OBJECT-TYPE
            SYNTAX Integer32
            MAX-ACCESS read-only
            STATUS current
            DESCRIPTION
               "hwXQoSIrsmTotalPacket "
            ::= { hwXQoSIrsmEntry 8 }
              
      hwXQoSIrsmDropPacket OBJECT-TYPE
            SYNTAX Integer32
            MAX-ACCESS read-only
            STATUS current
            DESCRIPTION
               "hwXQoSIrsmDropPacket "
            ::= { hwXQoSIrsmEntry 9 }


    -- alarm
                   
    hwXQoSNotifications OBJECT IDENTIFIER ::= { hwXQoSObjects 11 }

    hwXQoSCpDefendDiscardedRateAlarm NOTIFICATION-TYPE
        OBJECTS { hwXQoSCpDefendDiscardedPacketRate }
        STATUS current
        DESCRIPTION 
            "Rate alarm of packets in the attack defense."
            ::= { hwXQoSNotifications 1 }      
    hwXQoSQueueDiscardThresholdTrap NOTIFICATION-TYPE
     OBJECTS  {             
              hwXQoSFrameId ,
              hwXQoSSlotId ,   
              hwXQoSPortId ,
               hwXQoSTrapIfName , 
              hwXQoSTrapQueueId ,
              hwXQoSTrapDiscardPackets
              }
     STATUS   current
     DESCRIPTION
         "The SNMP trap is generated when the number of packages 
          that queue discard is larger than the configured threshold."
     ::= { hwXQoSNotifications 2 }        
     
    hwXQoSCpDefendDiscardedPacketAlarm NOTIFICATION-TYPE
    OBJECTS {
        hwXQoSCpDefendSlotId,
        hwXQoSCpDefendObjectIndex,
        hwXQoSCpDefendDiscardedPackets,
        hwXQoSCpDefendDiscardedThreshold,
        hwXQoSCpDefendChassisID
        }
     STATUS current
     DESCRIPTION 
    "The number of packets discarded by the cpu-defend policy exceed the threshold."
    ::= { hwXQoSNotifications 3 }      
            
    hwXQoSCpDefendDiscardedPacketAlarmClear NOTIFICATION-TYPE
    OBJECTS {
        hwXQoSCpDefendSlotId,
        hwXQoSCpDefendObjectIndex,
        hwXQoSCpDefendDiscardedPackets,
        hwXQoSCpDefendDiscardedThreshold,
        hwXQoSCpDefendChassisID         
        }
     STATUS current
     DESCRIPTION 
    "The number of packets discarded by the cpu-defend policy below the threshold."
    ::= { hwXQoSNotifications 4 } 

    hwXQoSCprlDiscardedPacketAlarm NOTIFICATION-TYPE
    OBJECTS {
        hwXQoSCpRateLimitIfIndex,
        hwXQoSCpRateLimitPeVidValue,
        hwXQoSCpRateLimitCeVidBegin 
        }
     STATUS current
     DESCRIPTION 
    "Number of packets discarded in the attack defense alarm."
    ::= { hwXQoSNotifications 5 }      
            
    hwXQoSCprlDiscardedPacketAlarmClear NOTIFICATION-TYPE
    OBJECTS {
        hwXQoSCpRateLimitIfIndex,
        hwXQoSCpRateLimitPeVidValue,
        hwXQoSCpRateLimitCeVidBegin
        }
     STATUS current
     DESCRIPTION 
    "Number of packets discarded in the attack defense alarm clearing."
    ::= { hwXQoSNotifications 6 } 

    hwXQoSRedirectNextHopChangedAlarm NOTIFICATION-TYPE
     OBJECTS  {             
              hwXQoSRedirectNextHopBehaviorName ,
              hwXQoSRedirectNextHopOldIp ,   
              hwXQoSRedirectNextHopNewIp
              }
     STATUS   current
     DESCRIPTION
         "The SNMP trap is the redirect next hop changed."
     ::= { hwXQoSNotifications 7 }  


    hwXQoSIrsmDelayAlarm NOTIFICATION-TYPE
     OBJECTS {
        hwXQoSIrsmSourceAddress,
        hwXQoSIrsmGroupAddress,
        hwXQoSIrsmTime,
        hwXQoSIrsmDelay,
        hwXQoSIrsmThreshold,
        hwXQoSIrsmUpstream,
        hwXQoSIrsmLocal 
     }
     STATUS current
     DESCRIPTION 
     "IRSM delay over threshold."
     ::= { hwXQoSNotifications 8 }      

    hwXQoSIrsmDropPacketAlarm NOTIFICATION-TYPE
    OBJECTS {
        hwXQoSIrsmSourceAddress,
        hwXQoSIrsmGroupAddress,
        hwXQoSIrsmTime,
        hwXQoSIrsmTotalPacket,
        hwXQoSIrsmDropPacket,
        hwXQoSIrsmUpstream,
        hwXQoSIrsmLocal
     }
     STATUS current
     DESCRIPTION 
     "IRSM multicast drop packets."
     ::= { hwXQoSNotifications 9 }      

    hwXQoSIrsmSynFrameDropAlarm NOTIFICATION-TYPE
    OBJECTS {
        hwXQoSIrsmSourceAddress,
        hwXQoSIrsmGroupAddress,
        hwXQoSIrsmTime 
     }
     STATUS current
     DESCRIPTION 
     "IRSM syn frame drop."
    ::= { hwXQoSNotifications 10 }      

         
    hwXQoSRuleFaileAlarm NOTIFICATION-TYPE
    OBJECTS {
        hwXQoSRuleFailInfo
        }
     STATUS current
     DESCRIPTION 
    "hwXQoSRuleFaileAlarm."
    ::= { hwXQoSNotifications 11 } 
    hwXQoSProfileUsedAlarm NOTIFICATION-TYPE
    OBJECTS {
        hwXQoSProfileName  
     }
     STATUS current
     DESCRIPTION 
     "Qos-profile used."
    ::= { hwXQoSNotifications 12 }      
    --port queue alarm
    hwXQoSPortQueueAlarm NOTIFICATION-TYPE
    OBJECTS {
        hwXQoSPortQueueAlarmIfIndex,
        hwXQoSPortQueueAlarmQueue,
        hwXQoSPortQueueAlarmTrunkIndex     
        }
     STATUS current
     DESCRIPTION 
    "hwXQoSPortQueueAlarm."
    ::= { hwXQoSNotifications 13 }  
    
    hwXQoSPortQueueAlarmClear NOTIFICATION-TYPE
    OBJECTS {
        hwXQoSPortQueueAlarmIfIndex,
        hwXQoSPortQueueAlarmQueue,
        hwXQoSPortQueueAlarmTrunkIndex       
        }
     STATUS current
     DESCRIPTION 
    "hwXQoSPortQueueAlarmClear."
    ::= { hwXQoSNotifications 14 } 
    --port queue alarm

   hwXQoSSecurityStormControlInterfaceTrap NOTIFICATION-TYPE
   OBJECTS { 
          hwXQoSSecurityStormControlInterfaceChassisId, 
          hwXQoSSecurityStormControlInterfaceSlotId, 
          hwXQoSSecurityStormControlInterfaceName, 
          hwXQoSSecurityStormControlInterfaceVlan}
       STATUS current
       DESCRIPTION 
       "The SNMP trap is generated when the status of interface is changed for storm-control."
       ::= { hwXQoSNotifications 15 }
--begin add by wangyonggui 176838, CAR/STAT Alarm
   
   hwXQoSResouceNotEnoughAlarmObjects OBJECT IDENTIFIER ::= { hwXQoSObjects 22 }
   
   hwXQoSStatResouceNotEnoughAlarm NOTIFICATION-TYPE
   OBJECTS { 
          hwXQoSStatResouceNotEnoughSlotId, 
          hwXQoSStatResouceNotEnoughStatType}
       STATUS current
       DESCRIPTION 
       "The SNMP trap is generated when the specific statistics resource is not enough."
       ::= { hwXQoSNotifications 16 }
   hwXQoSCARResouceNotEnoughAlarm NOTIFICATION-TYPE
   OBJECTS { 
          hwXQoSCARResouceNotEnoughSlotId, 
          hwXQoSCARResouceNotEnoughCARType}
       STATUS current
       DESCRIPTION 
       "The SNMP trap is generated when the specific car resource is not enough."
       ::= { hwXQoSNotifications 17 }
--end add by wangyonggui 176838, CAR/STAT Alarm

    hwXQoSGeneral OBJECT IDENTIFIER ::= { hwXQoSObjects 12 }
    
    hwXQoSFrameId  OBJECT-TYPE
        SYNTAX Integer32
        MAX-ACCESS read-only
        STATUS current
        DESCRIPTION "The ID of the frame."
        ::= { hwXQoSGeneral  1 }
        
    hwXQoSSlotId  OBJECT-TYPE
        SYNTAX Integer32        
        MAX-ACCESS read-only
        STATUS current
        DESCRIPTION "The ID of the slot that the interface is located."
        ::= { hwXQoSGeneral  2 }   
        
    hwXQoSPortId  OBJECT-TYPE
        SYNTAX Integer32        
        MAX-ACCESS read-only
        STATUS current
        DESCRIPTION "The ID of the port"
        ::= { hwXQoSGeneral  3 }     
                                                  
    hwXQoSTrapIfName  OBJECT-TYPE
        SYNTAX OCTET STRING (SIZE (1..31))
        MAX-ACCESS read-only
        STATUS current
        DESCRIPTION "The name of the interface."
        ::= { hwXQoSGeneral  4 } 
        
    hwXQoSTrapQueueId  OBJECT-TYPE
        SYNTAX  Integer32
        MAX-ACCESS read-only
        STATUS current
        DESCRIPTION "The ID of the queue giving an alarm."
        ::= { hwXQoSGeneral  5 }
      
      
    hwXQoSTrapDiscardPackets  OBJECT-TYPE
        SYNTAX  Counter64
        MAX-ACCESS read-only
        STATUS current
        DESCRIPTION "The number of the discarded packets."
        ::= { hwXQoSGeneral  6 }
        
        hwXQoSStormControlObjects OBJECT IDENTIFIER ::= { hwXQoSObjects 13 }

        hwXQoSStormControlTable OBJECT-TYPE
            SYNTAX SEQUENCE OF HwXQoSStormControlEntry
            MAX-ACCESS not-accessible
            STATUS current
            DESCRIPTION
                "A Table about storm-control configuration information."
            ::= { hwXQoSStormControlObjects 1 }

        
        hwXQoSStormControlEntry OBJECT-TYPE
            SYNTAX HwXQoSStormControlEntry
            MAX-ACCESS not-accessible
            STATUS current
            DESCRIPTION
                "Description."
            INDEX { hwXQoSStormControlIfIndex }
            ::= { hwXQoSStormControlTable 1 }

        
        HwXQoSStormControlEntry ::=
            SEQUENCE { 
                hwXQoSStormControlIfIndex
                    InterfaceIndex,
                hwXQoSStormControlBroadcastMinRate
                    Integer32,
                hwXQoSStormControlBroadcastMaxRate
                    Integer32,
                hwXQoSStormControlMulticastMinRate
                    Integer32,
                hwXQoSStormControlMulticastMaxRate
                    Integer32,
                hwXQoSStormControlAction
                    INTEGER,
                hwXQoSStormControlInterval
                    Integer32,
                hwXQoSStormControlTrapEnable
                    EnabledStatus,
                hwXQoSStormControlLogEnable
                    EnabledStatus,
                hwXQoSStormControlStatus
                    INTEGER,
                hwXQoSStormControlUnicastMinRate
                    Integer32,
                hwXQoSStormControlUnicastMaxRate
                    Integer32,
                hwXQoSStormControlBcMode
                    INTEGER,
                hwXQoSStormControlMcMode
                    INTEGER,
                hwXQoSStormControlUcMode
                    INTEGER                  
             }
             
        hwXQoSStormControlIfIndex OBJECT-TYPE
            SYNTAX InterfaceIndex
            MAX-ACCESS not-accessible
            STATUS current
            DESCRIPTION
                "The interface index,equal to ifIndex."
            ::= { hwXQoSStormControlEntry 1 }

        hwXQoSStormControlBroadcastMinRate OBJECT-TYPE
            SYNTAX Integer32 (0..14881000)
            MAX-ACCESS read-write
            STATUS current
            DESCRIPTION
                "The low water mark of broadcast packets rate. Unit: pps (packets per second).
                zero : storm-control function is not enable for broadcast packets."
            DEFVAL { 0 }
            ::= { hwXQoSStormControlEntry 2 }    

        hwXQoSStormControlBroadcastMaxRate OBJECT-TYPE
            SYNTAX Integer32 (0..14881000)
            MAX-ACCESS read-write
            STATUS current
            DESCRIPTION
                "The high water mark of broadcast packets rate. Unit: pps (packets per second).
                zero : storm-control function is not enable for broadcast packets."
            DEFVAL { 0 }
            ::= { hwXQoSStormControlEntry 3 }

        
        hwXQoSStormControlMulticastMinRate OBJECT-TYPE
            SYNTAX Integer32 (0..14881000)
            MAX-ACCESS read-write
            STATUS current
            DESCRIPTION
                "The low water mark of multicast packets rate. Unit: pps (packets per second).
                zero : storm-control function is not enable for multicast packets."
            DEFVAL { 0 }
            ::= { hwXQoSStormControlEntry 4 }

        
        hwXQoSStormControlMulticastMaxRate OBJECT-TYPE
            SYNTAX Integer32 (0..14881000)
            MAX-ACCESS read-write
            STATUS current
            DESCRIPTION
                "The high water mark of multicast packets rate. Unit: pps (packets per second).
                zero : storm-control function is not enable for multicast packets."
            DEFVAL { 0 }
            ::= { hwXQoSStormControlEntry 5 }


        hwXQoSStormControlAction OBJECT-TYPE
            SYNTAX INTEGER
                {
                none(1),
                block(2),
                shutdown(3)
                }
            MAX-ACCESS read-write
            STATUS current
            DESCRIPTION
                "storm-control action.
                none : no action will be taken.
                block: packets will be blocked if receiving-rate is higher than the high water mark and will be unblocked only when the receiving-rate drops below the low water mark.
                shutdown: the interface will be shutdown if receiving-rate is higher than the high water mark and the interface will NOT be open when the receiving-rate drops below the low water mark. To open the interface , use undo shutdown commond."
            DEFVAL { 1 }
            ::= { hwXQoSStormControlEntry 6 }
        

        hwXQoSStormControlInterval OBJECT-TYPE
            SYNTAX Integer32 (1..180)
            MAX-ACCESS read-write
            STATUS current
            DESCRIPTION
                "The interval that the broadcast storm or mutilcast storm will be checked. Unit: second."
            DEFVAL { 3 }
            ::= { hwXQoSStormControlEntry 7 } 
                
        hwXQoSStormControlTrapEnable OBJECT-TYPE
            SYNTAX EnabledStatus
            MAX-ACCESS read-write
            STATUS current
            DESCRIPTION
                "Enable or disable trap.
                enable(1): report trap when interface status changes.
                disable(2): do not report trap when interface status changes. "
            DEFVAL { 2 }
            ::= { hwXQoSStormControlEntry 8 }
            
        hwXQoSStormControlLogEnable OBJECT-TYPE
            SYNTAX EnabledStatus
            MAX-ACCESS read-write
            STATUS current
            DESCRIPTION
                "Enable or disable log.
                enable(1): record log when interface status changes.
                disable(2): do not record log when interface status changes. "
            DEFVAL { 2 }
            ::= { hwXQoSStormControlEntry 9 }

        
        hwXQoSStormControlStatus OBJECT-TYPE
            SYNTAX INTEGER
                {
                normal(1),
                broadcastBlocked(2),
                multicastBlocked(3),
                bothBlocked(4),
                shutdown(5),
                unicastBlocked(6),
                allBlocked(7),
                bcmcBlocked(8),
                bcucBlocked(9),
                ucmcBlocked(10)
                }
            MAX-ACCESS read-only
            STATUS current
            DESCRIPTION
                "The status of the interface.
                normal: no storm-control aciton is taken.
                broadcastBlocked: broadcast packets is blocked.
                multicastBlocked: multicast packets is blocked.
                bothBlocked: both the broadcast and multicast packets are blocked.
                shutdown: the interface is shutdown.
                unicastBlocked: unicast packets is blocked.
                allBlocked: broadcast multicast unicast packets is blocked.
                bcmcBlocked: both the broadcast and multicast packets are blocked.
                bcucBlocked: both the broadcast and unicast packets are blocked.
                ucmcBlocked: both the unicast and multicast packets are blocked."
            ::= { hwXQoSStormControlEntry 10 }  
            
        hwXQoSStormControlUnicastMinRate OBJECT-TYPE
            SYNTAX Integer32 (0..14881000)
            MAX-ACCESS read-write
            STATUS current
            DESCRIPTION
                "The low water mark of unicast packets rate. Unit: pps (packets per second).
                zero : storm-control function is not enable for unicast packets."
            DEFVAL { 0 }
            ::= { hwXQoSStormControlEntry 11 }    

        hwXQoSStormControlUnicastMaxRate OBJECT-TYPE
            SYNTAX Integer32 (0..14881000)
            MAX-ACCESS read-write
            STATUS current
            DESCRIPTION
                "The high water mark of unicast packets rate. Unit: pps (packets per second).
                zero : storm-control function is not enable for unicast packets."
            DEFVAL { 0 }
            ::= { hwXQoSStormControlEntry 12 }
            
        hwXQoSStormControlBcMode OBJECT-TYPE
            SYNTAX INTEGER {
                pps(0),
                kbps(1),
                percent(2),
                none(3)
                }
            MAX-ACCESS read-write
            STATUS current
            DESCRIPTION
                "The mode of broadcast packets.
                pps : (packets per second).
                kbps : (kbit per second).
                percent : (%).
                none: initialization."
            DEFVAL { 3 }
            ::= { hwXQoSStormControlEntry 13 } 
            
        hwXQoSStormControlMcMode OBJECT-TYPE
            SYNTAX INTEGER {
                pps(0),
                kbps(1),
                percent(2),
                none(3)
                }
            MAX-ACCESS read-write
            STATUS current
            DESCRIPTION
                "The mode of multicast packets.
                pps : (packets per second).
                kbps : (kbit per second).
                percent : (%).
                none: initialization."
            DEFVAL { 3 }
            ::= { hwXQoSStormControlEntry 14 }
            
        hwXQoSStormControlUcMode OBJECT-TYPE
            SYNTAX INTEGER {
                pps(0),
                kbps(1),
                percent(2),
                none(3)
                }
            MAX-ACCESS read-write
            STATUS current
            DESCRIPTION
                "The mode of unicast packets.
                pps : (packets per second).
                kbps : (kbit per second).
                percent : (%).
                none: initialization."
            DEFVAL { 3 }
            ::= { hwXQoSStormControlEntry 15 }                     
            
        hwXQoSStormControlNotification OBJECT IDENTIFIER ::= { hwXQoSObjects 14 }

        
        hwXQoSStormControlTrap NOTIFICATION-TYPE
            OBJECTS { hwXQoSStormControlBroadcastMinRate, hwXQoSStormControlBroadcastMaxRate, hwXQoSStormControlMulticastMinRate, hwXQoSStormControlMulticastMaxRate,  
                hwXQoSStormControlAction, hwXQoSStormControlInterval, hwXQoSStormControlStatus, hwXQoSStormControlUnicastMinRate, hwXQoSStormControlUnicastMaxRate, hwXQoSStormControlBcMode ,hwXQoSStormControlMcMode ,hwXQoSStormControlUcMode }
            STATUS current
            DESCRIPTION 
                "The SNMP trap is generated when the status of interface is changed for storm-control.
                hwXQoSStormControlBroadcastMinRate: The low water mark of broadcast packets rate.
                hwXQoSStormControlBroadcastMaxRate: The high water mark of broadcast packets rate.
                hwXQoSStormControlMulticastMinRate: The low water mark of multicast packets rate.
                hwXQoSStormControlMulticastMaxRate: The high water mark of multicast packets rate.                
                hwXQoSStormControlAction: The storm-control action.
                hwXQoSStormControlInterval: The interval that the broadcast storm or mutilcast storm will be checked.
                hwXQoSStormControlStatus: The status of the interface.
                hwXQoSStormControlUnicastMinRate: The low water mark of unicast packets rate.
                hwXQoSStormControlUniicastMaxRate: The high water mark of unicast packets rate.
                hwXQoSStormControlBcMode: The mode of Broadcast packets.
                hwXQoSStormControlMcMode: The mode of multicast packets.
                hwXQoSStormControlUcMode: The mode of unicast packets."
            ::= { hwXQoSStormControlNotification 1 }

                
                hwXQoSQueueStatisticsObjects OBJECT IDENTIFIER ::= { hwXQoSObjects 15 }

                
                hwXQoSQueueStatisticsTable OBJECT-TYPE
                        SYNTAX SEQUENCE OF HwXQoSQueueStatisticsEntry
                        MAX-ACCESS not-accessible
                        STATUS current
                        DESCRIPTION
                                "A Table about queue statistics."
                        ::= { hwXQoSQueueStatisticsObjects 1 }

                
                hwXQoSQueueStatisticsEntry OBJECT-TYPE
                        SYNTAX HwXQoSQueueStatisticsEntry
                        MAX-ACCESS not-accessible
                        STATUS current
                        DESCRIPTION
                                "The entry of queue statistics infomation."
                        INDEX { hwXQoSQueueStatisticsIngressIfIndex, hwXQoSQueueStatisticsEgressIfIndex, hwXQoSQueueStatisticsQueueIndex }
                        ::= { hwXQoSQueueStatisticsTable 1 }

                
                HwXQoSQueueStatisticsEntry ::=
                        SEQUENCE { 
                                hwXQoSQueueStatisticsIngressIfIndex
                                        InterfaceIndex,
                                hwXQoSQueueStatisticsEgressIfIndex
                                        InterfaceIndex,
                                hwXQoSQueueStatisticsQueueIndex
                                        INTEGER,
                                hwXQoSQueueStatisticsPassedPacketsCount
                                        Counter64,
                                hwXQosQueueStatisticsReset
                                        INTEGER,
                                hwXQoSQueueStatisticsRowStatus
                                        RowStatus
                                
                         }

                hwXQoSQueueStatisticsIngressIfIndex OBJECT-TYPE
                        SYNTAX InterfaceIndex
                        MAX-ACCESS not-accessible
                        STATUS current
                        DESCRIPTION
                                "The ingress interface index.
                                2147483647: invalid interface index, the statistics will be the count of packets of the egress interface and queue.
                                The ingress interface index and the egress interface index can not be 2147483647 at the same time."
                        ::= { hwXQoSQueueStatisticsEntry 1 }
                
                hwXQoSQueueStatisticsEgressIfIndex OBJECT-TYPE
                        SYNTAX InterfaceIndex
                        MAX-ACCESS not-accessible
                        STATUS current
                        DESCRIPTION
                                "The egress interface index.
                                2147483647: invalid interface index, the statistics will be the count of packets of the ingress interface and queue.
                                The ingress interface index and the egress interface index can not be 2147483647 at the same time. "
                        ::= { hwXQoSQueueStatisticsEntry 2 }

                hwXQoSQueueStatisticsQueueIndex OBJECT-TYPE
                        SYNTAX INTEGER
                                {
                                be(1),
                                af1(2),
                                af2(3),
                                af3(4),
                                af4(5),
                                ef(6),
                                cs6(7),
                                cs7(8)
                                }
                        MAX-ACCESS not-accessible
                        STATUS current
                        DESCRIPTION
                                "The queue index."
                        ::= { hwXQoSQueueStatisticsEntry 3 }
                        
                hwXQoSQueueStatisticsPassedPacketsCount OBJECT-TYPE
                        SYNTAX Counter64
                        MAX-ACCESS read-only
                        STATUS current
                        DESCRIPTION
                                "The passed packets count.
                                If the ingress interface index is 2147483647, this node will be the count of passed packets of the specified queue of the ingress interface. 
                                If the egress interface index is 2147483647, this node will be the count of passed packets of the specified queue of the ingress interface.
                                If none of the ingress and egress interface is 2147483647, this node will be the count of passed packets which is from the ingress interface to 
                                the egress interface at the specified queue.
                                The ingress interface index and the egress interface index can not be 2147483647 at the same time ."
                        ::= { hwXQoSQueueStatisticsEntry 4 }
                        
        hwXQosQueueStatisticsReset OBJECT-TYPE
                        SYNTAX INTEGER
                                {
                                reset(1)                               
                                }
                        MAX-ACCESS read-create
                        STATUS current
                        DESCRIPTION
                                "Set this node to reset the counter.
                                 Reset(1) will be returned if this node is read."
                        ::= { hwXQoSQueueStatisticsEntry 5 }
                
                hwXQoSQueueStatisticsRowStatus OBJECT-TYPE
                        SYNTAX RowStatus
                        MAX-ACCESS read-create
                        STATUS current
                        DESCRIPTION
                                "RowStatus. Three actions are used:
                                active,createandgo, destroy"
                        ::= { hwXQoSQueueStatisticsEntry 6 }
                         
                         
               hwXQoSPortStatisticsDropObjects OBJECT IDENTIFIER ::= { hwXQoSObjects 16 }

                
               hwXQoSPortStatisticsDropTable OBJECT-TYPE
                        SYNTAX SEQUENCE OF HwXQoSPortStatisticsDropEntry
                        MAX-ACCESS not-accessible
                        STATUS current
                        DESCRIPTION
                                "A table about drop packets statistics of port."
                        ::= { hwXQoSPortStatisticsDropObjects 1 }

                
                hwXQoSPortStatisticsDropEntry OBJECT-TYPE
                        SYNTAX HwXQoSPortStatisticsDropEntry
                        MAX-ACCESS not-accessible
                        STATUS current
                        DESCRIPTION
                                "The entry about drop packets statistics of port."
                        INDEX { hwXQoSPortStatisticsDropIfIndex}
                        ::= { hwXQoSPortStatisticsDropTable 1 }

                
                HwXQoSPortStatisticsDropEntry ::=
                        SEQUENCE { 
                                hwXQoSPortStatisticsDropIfIndex
                                        InterfaceIndex,
                                hwXQoSPortStatisticsDropPacketsCount
                                        Counter64,
                                hwXQosPortStatisticsDropReset
                                        INTEGER,
                                hwXQosPortStatisticsDropResetTime
                                        TimeTicks

                         }

                hwXQoSPortStatisticsDropIfIndex OBJECT-TYPE
                        SYNTAX InterfaceIndex
                        MAX-ACCESS not-accessible
                        STATUS current
                        DESCRIPTION
                                "The interface index."
                        ::= { hwXQoSPortStatisticsDropEntry 1 } 
                        
        
                hwXQoSPortStatisticsDropPacketsCount OBJECT-TYPE
                        SYNTAX Counter64
                        MAX-ACCESS read-only
                        STATUS current
                        DESCRIPTION
                                "The dropped packets count of the port."
                        ::= { hwXQoSPortStatisticsDropEntry 2 }
                        
                hwXQosPortStatisticsDropReset OBJECT-TYPE
                        SYNTAX INTEGER
                                {
                                reset(1)                               
                                }
                        MAX-ACCESS read-write
                        STATUS current
                        DESCRIPTION
                                "Set this node to reset the counter.
                                 Reset(1) will be returned if this node is read."
                        ::= { hwXQoSPortStatisticsDropEntry 3 }    
                          
                hwXQosPortStatisticsDropResetTime OBJECT-TYPE
                        SYNTAX TimeTicks
                        MAX-ACCESS read-only
                        STATUS current
                        DESCRIPTION
                                "The value of sysUpTime on the most recent occasion at
                                 which one of this interface's counters
                                 suffered a discontinuity. If no such discontinuities have
                                 occurred since the last re-initialization of the local
                                 management subsystem, then this object contains a zero
                                 value."
                        ::= { hwXQoSPortStatisticsDropEntry 4 }

                     
                        
                hwXQoSQueueStatisticsDropObjects OBJECT IDENTIFIER ::= { hwXQoSObjects 17 }

                
                hwXQoSQueueStatisticsDropTable OBJECT-TYPE
                        SYNTAX SEQUENCE OF HwXQoSQueueStatisticsDropEntry
                        MAX-ACCESS not-accessible
                        STATUS current
                        DESCRIPTION
                                "A table about drop packets statistics of queue."
                        ::= { hwXQoSQueueStatisticsDropObjects 1 }

                
                hwXQoSQueueStatisticsDropEntry OBJECT-TYPE
                        SYNTAX HwXQoSQueueStatisticsDropEntry
                        MAX-ACCESS not-accessible
                        STATUS current
                        DESCRIPTION
                                "The entry about drop packets statistics of queue."
                        INDEX { hwXQoSQueueStatisticsDropIfIndex,hwXQoSQueueStatisticsDropQueueIndex }
                        ::= { hwXQoSQueueStatisticsDropTable 1 }

                
                HwXQoSQueueStatisticsDropEntry ::=
                        SEQUENCE { 
                                hwXQoSQueueStatisticsDropIfIndex
                                        InterfaceIndex,
                                hwXQoSQueueStatisticsDropQueueIndex
                                        INTEGER,
                                hwXQoSQueueStatisticsDropPacketsCount
                                        Counter64,
                                hwXQosQueueStatisticsDropReset
                                        INTEGER,
                                hwXQosQueueStatisticsDropResetTime
                                        TimeTicks                             
                         }

                hwXQoSQueueStatisticsDropIfIndex OBJECT-TYPE
                        SYNTAX InterfaceIndex
                        MAX-ACCESS not-accessible
                        STATUS current
                        DESCRIPTION
                                "The interface index."
                        ::= { hwXQoSQueueStatisticsDropEntry 1 }
                
              
                hwXQoSQueueStatisticsDropQueueIndex OBJECT-TYPE
                        SYNTAX INTEGER
                                {
                                be(1),
                                af1(2),
                                af2(3),
                                af3(4),
                                af4(5),
                                ef(6),
                                cs6(7),
                                cs7(8)
                                }
                        MAX-ACCESS not-accessible
                        STATUS current
                        DESCRIPTION
                                "The queue index."
                        ::= { hwXQoSQueueStatisticsDropEntry 2 }
                        
                hwXQoSQueueStatisticsDropPacketsCount OBJECT-TYPE
                        SYNTAX Counter64
                        MAX-ACCESS read-only
                        STATUS current
                        DESCRIPTION
                                "The dropped packets count of the queue."
                        ::= { hwXQoSQueueStatisticsDropEntry 3 }
                        
               hwXQosQueueStatisticsDropReset OBJECT-TYPE
                        SYNTAX INTEGER
                                {
                                reset(1)                               
                                }
                        MAX-ACCESS read-write
                        STATUS current
                        DESCRIPTION
                                "Set this node to reset the counter.
                                 Reset(1) will be returned if this node is read."
                        ::= { hwXQoSQueueStatisticsDropEntry 4 } 
               
               hwXQosQueueStatisticsDropResetTime OBJECT-TYPE
                        SYNTAX TimeTicks
                        MAX-ACCESS read-only
                        STATUS current
                        DESCRIPTION
                                "The value of sysUpTime on the most recent occasion at
                                 which  one of this queue's counters
                                 suffered a discontinuity. If no such discontinuities have
                                 occurred since the last re-initialization of the local
                                 management subsystem, then this object contains a zero
                                 value."

                        ::= { hwXQoSQueueStatisticsDropEntry 5 }
                        
              --rulefail  
    
        hwXQoSRuleFailObjects OBJECT IDENTIFIER ::= { hwXQoSObjects 18 }

        hwXQoSRuleFailTable OBJECT-TYPE
            SYNTAX SEQUENCE OF HwXQoSRuleFailEntry
            MAX-ACCESS not-accessible
            STATUS current
            DESCRIPTION
                "hwXQoSRuleFailTable"
            ::= { hwXQoSRuleFailObjects 1 }

        hwXQoSRuleFailEntry OBJECT-TYPE
            SYNTAX HwXQoSRuleFailEntry
            MAX-ACCESS not-accessible
            STATUS current
            DESCRIPTION
                "hwXQoSRuleFailEntry"
            INDEX { hwXQoSRuleFailInfo }
            ::= { hwXQoSRuleFailTable 1 }

        HwXQoSRuleFailEntry ::=
            SEQUENCE { 
                hwXQoSRuleFailInfo
                    OCTET STRING
                 }  

        hwXQoSRuleFailInfo OBJECT-TYPE
            SYNTAX OCTET STRING (SIZE (1..32))
            MAX-ACCESS read-only
            STATUS current
            DESCRIPTION
                "hwXQoSRuleFailInfo."
            ::= { hwXQoSRuleFailEntry 1 }
                       
               
-- profile alarm
        hwXQoSProfileObjects OBJECT IDENTIFIER ::= { hwXQoSObjects 19 }

        hwXQoSProfileTable OBJECT-TYPE
            SYNTAX SEQUENCE OF HwXQoSProfileEntry
            MAX-ACCESS not-accessible
            STATUS current
            DESCRIPTION
                "A table of the qos-profile"
            ::= { hwXQoSProfileObjects 1 }

        hwXQoSProfileEntry OBJECT-TYPE
            SYNTAX HwXQoSProfileEntry
            MAX-ACCESS not-accessible
            STATUS current
            DESCRIPTION
                "A table of the redirect next hop information"
            INDEX { hwXQoSProfileName }
            ::= { hwXQoSProfileTable 1 }

        HwXQoSProfileEntry ::=
            SEQUENCE { 
                hwXQoSProfileName
                    OCTET STRING
             }  
-- BEGIN: mod by l00248629, 2014/03/21
        hwXQoSProfileName OBJECT-TYPE
            SYNTAX OCTET STRING (SIZE (1..63))
            MAX-ACCESS read-only
            STATUS current
            DESCRIPTION
                "Qos-profile name."
            ::= { hwXQoSProfileEntry 1 }                
-- END: mod by l00248629, 2014/03/21
          --port queue alarm
           hwXQoSPortQueueAlarmObjects OBJECT IDENTIFIER ::= { hwXQoSObjects 20 }

        hwXQoSPortQueueAlarmTable OBJECT-TYPE
            SYNTAX SEQUENCE OF HwXQoSPortQueueAlarmEntry
            MAX-ACCESS not-accessible
            STATUS current
            DESCRIPTION
                "hwXQoSPortQueueAlarmTable"
            ::= { hwXQoSPortQueueAlarmObjects 1 }

        hwXQoSPortQueueAlarmEntry OBJECT-TYPE
            SYNTAX HwXQoSPortQueueAlarmEntry
            MAX-ACCESS not-accessible
            STATUS current
            DESCRIPTION
                "hwXQoSPortQueueAlarmEntry"
            INDEX { hwXQoSPortQueueAlarmIfIndex }
            ::= { hwXQoSPortQueueAlarmTable 1 }

        HwXQoSPortQueueAlarmEntry ::=
            SEQUENCE { 
                hwXQoSPortQueueAlarmIfIndex
                    InterfaceIndex,
                hwXQoSPortQueueAlarmQueue
                    OCTET STRING,
                            hwXQoSPortQueueAlarmTrunkIndex
                                InterfaceIndex
                 }   
                 
        hwXQoSPortQueueAlarmIfIndex OBJECT-TYPE
                SYNTAX InterfaceIndex
                MAX-ACCESS read-only
                STATUS current
                DESCRIPTION
                        "The interface index."
                ::= { hwXQoSPortQueueAlarmEntry 1 }  
                      
        hwXQoSPortQueueAlarmQueue OBJECT-TYPE
            SYNTAX OCTET STRING (SIZE (1..4))
            MAX-ACCESS read-write
            STATUS current
            DESCRIPTION
                "hwXQoSPortQueueAlarmQueue."
            ::= { hwXQoSPortQueueAlarmEntry 2 }  
 
                hwXQoSPortQueueAlarmTrunkIndex OBJECT-TYPE
                SYNTAX InterfaceIndex
                MAX-ACCESS read-write
                STATUS current
                DESCRIPTION
                        "The trunk interface index."
                ::= { hwXQoSPortQueueAlarmEntry 3 }  
-- BEGIN: Added by s00197646, 2013/12/10  
		hwXQoSPortQueueAlarmExTable OBJECT-TYPE
            SYNTAX SEQUENCE OF HwXQoSPortQueueAlarmExEntry
            MAX-ACCESS not-accessible
            STATUS current
            DESCRIPTION
                "hwXQoSPortQueueAlarmExTable"
            ::= { hwXQoSPortQueueAlarmObjects 2 }
        hwXQoSPortQueueAlarmExEntry OBJECT-TYPE
            SYNTAX HwXQoSPortQueueAlarmExEntry
            MAX-ACCESS not-accessible
            STATUS current
            DESCRIPTION
                "hwXQoSPortQueueAlarmExEntry"
            INDEX { hwXQoSPortQueueAlarmExIfIndex,
					hwXQoSPortQueueAlarmExQueue}
            ::= { hwXQoSPortQueueAlarmExTable 1 }
        HwXQoSPortQueueAlarmExEntry ::=
            SEQUENCE { 
                hwXQoSPortQueueAlarmExIfIndex
                    InterfaceIndex,
                hwXQoSPortQueueAlarmExQueue
                    INTEGER,
                hwXQoSPortQueueAlarmExBuffer
                    Integer32
                 }   
        hwXQoSPortQueueAlarmExIfIndex OBJECT-TYPE
                SYNTAX InterfaceIndex
                MAX-ACCESS read-only
                STATUS current
                DESCRIPTION
                        "The interface index."
                ::= { hwXQoSPortQueueAlarmExEntry 1 }  
        hwXQoSPortQueueAlarmExQueue OBJECT-TYPE
				SYNTAX INTEGER
              {
                be(1),
                af1(2), 
                af2(3),
                af3(4),
                af4(5),
                ef(6),
                cs6(7),
                cs7(8)
               }
				MAX-ACCESS read-only
				STATUS current
				DESCRIPTION
				" This object indicates the priority of a class queue where statistics are queried.
					The value can be:
					1 be
					2 af1
					3 af2
					4 af3	
					5 af4
					6 ef
					7 cs6
					8 cs7       
					"
				::= { hwXQoSPortQueueAlarmExEntry 2 }  
        hwXQoSPortQueueAlarmExBuffer OBJECT-TYPE
                SYNTAX Integer32
                MAX-ACCESS read-only
                STATUS current
                DESCRIPTION
                        "The port queue alarm buffer."
                ::= { hwXQoSPortQueueAlarmExEntry 3 }  
-- END: Added by s00197646, 2013/12/10      
 --port queue alarm
    ---begin add by wangyonggui 176838, CAR/STAT Alarm
          hwXQoSStatResouceNotEnoughAlarmTable OBJECT-TYPE
                        SYNTAX SEQUENCE OF HwXQoSStatResouceNotEnoughAlarmEntry
                        MAX-ACCESS not-accessible
                        STATUS current
                        DESCRIPTION
                                "hwXQoSStatResouceNotEnoughAlarmTable"
                        ::= { hwXQoSResouceNotEnoughAlarmObjects 1 }
                        
              hwXQoSStatResouceNotEnoughAlarmEntry OBJECT-TYPE
            SYNTAX HwXQoSStatResouceNotEnoughAlarmEntry
            MAX-ACCESS not-accessible
            STATUS current
            DESCRIPTION
                "hwXQoSStatResouceNotEnoughAlarmEntry"
            INDEX { hwXQoSStatResouceNotEnoughSlotId, hwXQoSStatResouceNotEnoughStatType }
            ::= { hwXQoSStatResouceNotEnoughAlarmTable 1 }
            
              HwXQoSStatResouceNotEnoughAlarmEntry ::=
            SEQUENCE { 
                  hwXQoSStatResouceNotEnoughSlotId      
                        Integer32,
                  hwXQoSStatResouceNotEnoughStatType
                        OCTET STRING
                 }                 
                  
            hwXQoSStatResouceNotEnoughSlotId OBJECT-TYPE
                    SYNTAX Integer32 (1..128)
                MAX-ACCESS read-only
                STATUS current
                DESCRIPTION
                "Slot ID of the LPU where the stastitics resource is insufficient"
                 ::= { hwXQoSStatResouceNotEnoughAlarmEntry 1 }     
            hwXQoSStatResouceNotEnoughStatType OBJECT-TYPE
                    SYNTAX OCTET STRING (SIZE (1..511))
                MAX-ACCESS read-only
                STATUS current
                DESCRIPTION
                "Type of insufficient statistics resource"
                ::= { hwXQoSStatResouceNotEnoughAlarmEntry 2 }
            hwXQoSCARResouceNotEnoughAlarmTable OBJECT-TYPE
                        SYNTAX SEQUENCE OF HwXQoSCARResouceNotEnoughAlarmEntry
                        MAX-ACCESS not-accessible
                        STATUS current
                        DESCRIPTION
                                "hwXQoSCARResouceNotEnoughAlarmTable"
                        ::= { hwXQoSResouceNotEnoughAlarmObjects 2 }
                        
              hwXQoSCARResouceNotEnoughAlarmEntry OBJECT-TYPE
            SYNTAX HwXQoSCARResouceNotEnoughAlarmEntry
            MAX-ACCESS not-accessible
            STATUS current
            DESCRIPTION
                "hwXQoSCARResouceNotEnoughAlarmEntry"
            INDEX { hwXQoSCARResouceNotEnoughSlotId, hwXQoSCARResouceNotEnoughCARType }
            ::= { hwXQoSCARResouceNotEnoughAlarmTable 1 }
            
              HwXQoSCARResouceNotEnoughAlarmEntry ::=
            SEQUENCE { 
                  hwXQoSCARResouceNotEnoughSlotId      
                        Integer32,
                  hwXQoSCARResouceNotEnoughCARType
                        OCTET STRING
                 }                 
                  
            hwXQoSCARResouceNotEnoughSlotId OBJECT-TYPE
                    SYNTAX Integer32 (1..128)
                MAX-ACCESS read-only
                STATUS current
                DESCRIPTION
                "Slot ID of the LPU where the CAR resource is insufficient"
                 ::= { hwXQoSCARResouceNotEnoughAlarmEntry 1 }     
            hwXQoSCARResouceNotEnoughCARType OBJECT-TYPE
                    SYNTAX OCTET STRING (SIZE (1..511))
                MAX-ACCESS read-only
                STATUS current
                DESCRIPTION
                "Type of insufficient car resource"
                ::= { hwXQoSCARResouceNotEnoughAlarmEntry 2 }
                 --end add by wangyonggui 176838, CAR/STAT Alarm   
-- ******************************************************************
--
--   hwXQoSPortQueueStatisticsTable
--   hwXQoSQppbPolicyStatisticsTable   
--             w00164261
--
--                   
-- ******************************************************************

      hwXQoSQppbPolicyStatisticsTable OBJECT-TYPE
          SYNTAX      SEQUENCE OF HwXQoSQppbPolicyStatisticsEntry
          MAX-ACCESS  not-accessible
          STATUS      current
          DESCRIPTION
              " This table is used to query the statistics of qppb. "
          ::= { hwXQoSBaObjects 37 }
                    
      hwXQoSQppbPolicyStatisticsEntry OBJECT-TYPE
          SYNTAX HwXQoSQppbPolicyStatisticsEntry
          MAX-ACCESS not-accessible
          STATUS current
          DESCRIPTION
              "hwXQoSQppbPolicyStatisticsEntry" 
          INDEX  { hwXQoSQppbPolicyLocalID,
                   hwXQoSQppbPolicyDirection,
                   hwXQoSQppbPolicyStatisticsInterfaceIndex }    
          ::= { hwXQoSQppbPolicyStatisticsTable 1 }           

      HwXQoSQppbPolicyStatisticsEntry ::=
        SEQUENCE {  
                hwXQoSQppbPolicyLocalID
                    Integer32,    
                hwXQoSQppbPolicyDirection
                    INTEGER,         
                hwXQoSQppbPolicyStatisticsInterfaceIndex
                    InterfaceIndex,                                          
                hwXQoSQppbPolicyStatisticsReset  
                    INTEGER,                         
                hwXQoSQppbPolicyMatchedPackets 
                    Counter64,                     
                hwXQoSQppbPolicyMatchedBytes
                    Counter64,             
                hwXQoSQppbPolicyPassedPackets 
                    Counter64, 
                hwXQoSQppbPolicyPassedBytes    
                    Counter64,
                hwXQoSQppbPolicyDropedPackets
                    Counter64,
                hwXQoSQppbPolicyDropedBytes
                    Counter64,
                -- begin by chenzhe for qppb stat    
                hwXQoSQppbPolicyMatchPacketsRate
                    Counter64,
                hwXQoSQppbPolicyMatchBytesRate
                    Counter64
          -- end by chenzhe for qppb stat
                               }      
                               
                               
      hwXQoSQppbPolicyLocalID  OBJECT-TYPE
            SYNTAX Integer32
            MAX-ACCESS read-only
            STATUS current
            DESCRIPTION
            "qos-local-id <1~31>"
            ::= { hwXQoSQppbPolicyStatisticsEntry 1 }

       
      
      hwXQoSQppbPolicyDirection  OBJECT-TYPE
            SYNTAX INTEGER
              {
                inbound(1),
                outbound(2) 
              }
            MAX-ACCESS read-only
            STATUS current
            DESCRIPTION
            " This object indicates the direction where statistics are queried.
              The value can be:
              1: inbound
              2: outbound  "
            ::= { hwXQoSQppbPolicyStatisticsEntry 2 }
 
      
      hwXQoSQppbPolicyStatisticsInterfaceIndex  OBJECT-TYPE
            SYNTAX   InterfaceIndex
            MAX-ACCESS read-only
            STATUS current
            DESCRIPTION
            " This object indicates the interface index. "     
            ::= { hwXQoSQppbPolicyStatisticsEntry 3 }
       
  
          
      hwXQoSQppbPolicyStatisticsReset  OBJECT-TYPE
            SYNTAX INTEGER 
            {
                reset(1)
            }
            MAX-ACCESS read-write
            STATUS current
            DESCRIPTION
            " This object indicates the statistics are reset.  "    
            ::= { hwXQoSQppbPolicyStatisticsEntry 4 }   
       
    
      hwXQoSQppbPolicyMatchedPackets OBJECT-TYPE
            SYNTAX  Counter64
            MAX-ACCESS read-only
            STATUS current
            DESCRIPTION
            " This object indicates the number of matched packets. "    
            ::= { hwXQoSQppbPolicyStatisticsEntry 5 }   
            
            
      hwXQoSQppbPolicyMatchedBytes OBJECT-TYPE
            SYNTAX  Counter64
            MAX-ACCESS read-only
            STATUS current
            DESCRIPTION
            " This object indicates the number of matched bytes. "    
            ::= { hwXQoSQppbPolicyStatisticsEntry 6 }      


      hwXQoSQppbPolicyPassedPackets OBJECT-TYPE
            SYNTAX  Counter64
            MAX-ACCESS read-only
            STATUS current
            DESCRIPTION
            " This object indicates the number of passed packets. "    
            ::= { hwXQoSQppbPolicyStatisticsEntry 7 }    


      hwXQoSQppbPolicyPassedBytes OBJECT-TYPE
            SYNTAX  Counter64
            MAX-ACCESS read-only
            STATUS current
            DESCRIPTION
            " This object indicates the number of passed bytes. "    
            ::= { hwXQoSQppbPolicyStatisticsEntry 8 }   


      hwXQoSQppbPolicyDropedPackets OBJECT-TYPE
            SYNTAX  Counter64
            MAX-ACCESS read-only
            STATUS current
            DESCRIPTION
            " This object indicates the number of droped packets. "    
            ::= { hwXQoSQppbPolicyStatisticsEntry 9 }          


      hwXQoSQppbPolicyDropedBytes OBJECT-TYPE
            SYNTAX  Counter64
            MAX-ACCESS read-only
            STATUS current
            DESCRIPTION
            " This object indicates the number of droped bytes. "     
            ::= { hwXQoSQppbPolicyStatisticsEntry 10 }
    --   begin by chenzhe for qppb stat
      hwXQoSQppbPolicyMatchPacketsRate OBJECT-TYPE
            SYNTAX  Counter64
            MAX-ACCESS read-only
            STATUS current
            DESCRIPTION
            " This object indicates the rate of matched packets. "    
            ::= { hwXQoSQppbPolicyStatisticsEntry 11 }          


      hwXQoSQppbPolicyMatchBytesRate OBJECT-TYPE
            SYNTAX  Counter64
            MAX-ACCESS read-only
            STATUS current
            DESCRIPTION
            " This object indicates the rate of matched bytes. "     
            ::= { hwXQoSQppbPolicyStatisticsEntry 12 }
                  
    --   end by chenzhe for qppb stat  
    --   Beg addeded by w00164261 for qos phb enable <domain-name> [ vlan ] [vlan-id]   
      hwXQoSIfPhbEnableTable OBJECT-TYPE
            SYNTAX SEQUENCE OF HwXQoSIfPhbEnableEntry
            MAX-ACCESS not-accessible
            STATUS current
            DESCRIPTION
            "qos phb enable <domain-name> [ vlan ] [vlan-id]."
            ::= { hwXQoSBaObjects 38 }

    
      hwXQoSIfPhbEnableEntry OBJECT-TYPE
            SYNTAX HwXQoSIfPhbEnableEntry
            MAX-ACCESS not-accessible
            STATUS current
            DESCRIPTION
            "hwXQoSIfPhbEnableEntry."
            INDEX { hwXQoSIfPhbEnableIfIndex, hwXQoSIfPhbEnableVlanId }
            ::= { hwXQoSIfPhbEnableTable 1 }

    
      HwXQoSIfPhbEnableEntry ::=
        SEQUENCE { 
            hwXQoSIfPhbEnableIfIndex
                Integer32, 
            hwXQoSIfPhbEnableVlanId
                Integer32,  
            hwXQoSIfPhbEnableDomainName
                OCTET STRING,
            hwXQoSIfPhbEnableRowStatus
                RowStatus    
         }

      hwXQoSIfPhbEnableIfIndex OBJECT-TYPE
            SYNTAX Integer32
            MAX-ACCESS read-only
            STATUS current
            DESCRIPTION
            "The value of this object identifies the interface index."
            ::= { hwXQoSIfPhbEnableEntry 1 }

      hwXQoSIfPhbEnableVlanId OBJECT-TYPE
           SYNTAX Integer32 (0 | 1..4094)
           MAX-ACCESS read-only
           STATUS current
           DESCRIPTION
            "The value of this object identifies the VLAN ID of the interface."
            ::= { hwXQoSIfPhbEnableEntry 2 }

      hwXQoSIfPhbEnableDomainName OBJECT-TYPE
            SYNTAX OCTET STRING (SIZE (1..31))
            MAX-ACCESS read-create
            STATUS current
            DESCRIPTION
            "This object indicates the name of the DS domain.The value of the object ranges from 1 to 31.The name cannot contain Chinese characters."
            ::= { hwXQoSIfPhbEnableEntry 3 }

    
      hwXQoSIfPhbEnableRowStatus OBJECT-TYPE
            SYNTAX RowStatus
            MAX-ACCESS read-create
            STATUS current
            DESCRIPTION
            "This value of this object identifies the row status.The value can be any of the following:CreateAndGo(4), Destroy(6),Active(1)."
            ::= { hwXQoSIfPhbEnableEntry 4 }

      --   End modified by w00164261 for qos phb enable <domain-name> [ vlan ] [vlan-id]
                                                                       
        --   Beg add by w00176838 for remark payload-dscp
       
      hwXQoSIfRemarkDscpTable OBJECT-TYPE
            SYNTAX SEQUENCE OF HwXQoSIfRemarkDscpEntry
            MAX-ACCESS not-accessible
            STATUS current
            DESCRIPTION
            "enable to remark DSCP of the payload. "
            ::= { hwXQoSBaObjects 39 }

    
      hwXQoSIfRemarkDscpEntry OBJECT-TYPE
            SYNTAX HwXQoSIfRemarkDscpEntry
            MAX-ACCESS not-accessible
            STATUS current
            DESCRIPTION
            "hwXQoSIfRemarkDscpEntry."
            INDEX { hwXQoSIfRemarkDscpIfIndex }
            ::= { hwXQoSIfRemarkDscpTable 1 }

    
      HwXQoSIfRemarkDscpEntry ::=
        SEQUENCE { 
            hwXQoSIfRemarkDscpIfIndex
                Integer32,     
            hwXQoSIfRemarkDscpRowStatus
                RowStatus    
         }

      hwXQoSIfRemarkDscpIfIndex OBJECT-TYPE
            SYNTAX Integer32
            MAX-ACCESS read-only
            STATUS current
            DESCRIPTION
            "The value of this object identifies the interface index."
            ::= { hwXQoSIfRemarkDscpEntry 1 }
      
         hwXQoSIfRemarkDscpRowStatus OBJECT-TYPE
            SYNTAX RowStatus
            MAX-ACCESS read-create
            STATUS current
            DESCRIPTION
            "This value of this object identifies the row status.The value can be any of the following:CreateAndGo(4), Destroy(6),Active(1)."
            ::= { hwXQoSIfRemarkDscpEntry 2 }
            
           
-- ******************************************************************
--
--   hwXQoSQppbGlobalStatisticsTable   
--   add by l00174933
--
--                   
-- ******************************************************************
      hwXQoSQppbGlobalStatisticsTable OBJECT-TYPE
          SYNTAX      SEQUENCE OF HwXQoSQppbGlobalStatisticsEntry
          MAX-ACCESS  not-accessible
          STATUS      current
          DESCRIPTION
              " This table is used to query the global statistics of qppb. "
          ::= { hwXQoSBaObjects 40 }
                    
      hwXQoSQppbGlobalStatisticsEntry OBJECT-TYPE
          SYNTAX HwXQoSQppbGlobalStatisticsEntry
          MAX-ACCESS not-accessible
          STATUS current
          DESCRIPTION
              "hwXQoSQppbGlobalStatisticsEntry" 
          INDEX  { hwXQoSQppbGlobalStatisticsPolicyName,
                   hwXQoSQppbGlobalStatisticsLocalID,
                   hwXQoSQppbGlobalStatisticsDirection } 
          ::= { hwXQoSQppbGlobalStatisticsTable 1 }

      HwXQoSQppbGlobalStatisticsEntry ::=
        SEQUENCE {  
                hwXQoSQppbGlobalStatisticsPolicyName  
                    OCTET STRING,
                hwXQoSQppbGlobalStatisticsLocalID  
                    Integer32,
                hwXQoSQppbGlobalStatisticsDirection  
                    INTEGER,
                hwXQoSQppbGlobalStatisticsReset  
                    INTEGER,                         
                hwXQoSQppbGlobalStatisticsMatchedPackets 
                    Counter64,                     
                hwXQoSQppbGlobalStatisticsMatchedBytes
                    Counter64,             
                hwXQoSQppbGlobalStatisticsPassedPackets 
                    Counter64, 
                hwXQoSQppbGlobalStatisticsPassedBytes    
                    Counter64,
                hwXQoSQppbGlobalStatisticsDropedPackets
                    Counter64,
                hwXQoSQppbGlobalStatisticsDropedBytes
                    Counter64,   
                hwXQoSQppbGlobalStatisticsMatchPacketsRate
                    Counter64,
                hwXQoSQppbGlobalStatisticsMatchBytesRate
                    Counter64
              }      
                 
      hwXQoSQppbGlobalStatisticsPolicyName  OBJECT-TYPE
            SYNTAX   OCTET STRING (SIZE (1..31))
            MAX-ACCESS read-only
            STATUS current
            DESCRIPTION
            " This object indicates the QPPB policy name. "     
            ::= { hwXQoSQppbGlobalStatisticsEntry 1 }  
                               
      hwXQoSQppbGlobalStatisticsLocalID  OBJECT-TYPE
            SYNTAX Integer32
            MAX-ACCESS read-only
            STATUS current
            DESCRIPTION
            "qos-local-id <1~31>"
            ::= { hwXQoSQppbGlobalStatisticsEntry 2 }
      
      hwXQoSQppbGlobalStatisticsDirection  OBJECT-TYPE
            SYNTAX INTEGER
              {
                inbound(1),
                outbound(2) 
              }
            MAX-ACCESS read-only
            STATUS current
            DESCRIPTION
            " This object indicates the direction where statistics are queried.
              The value can be:
              1: inbound
              2: outbound  "
            ::= { hwXQoSQppbGlobalStatisticsEntry 3 }      
      
          
      hwXQoSQppbGlobalStatisticsReset  OBJECT-TYPE
            SYNTAX INTEGER 
            {
                reset(1)
            }
            MAX-ACCESS read-write
            STATUS current
            DESCRIPTION
            " This object indicates the statistics are reset.  "    
            ::= { hwXQoSQppbGlobalStatisticsEntry 4 } 
    
      hwXQoSQppbGlobalStatisticsMatchedPackets OBJECT-TYPE
            SYNTAX  Counter64
            MAX-ACCESS read-only
            STATUS current
            DESCRIPTION
            " This object indicates the number of matched packets. "    
            ::= { hwXQoSQppbGlobalStatisticsEntry 5 } 
            
      hwXQoSQppbGlobalStatisticsMatchedBytes OBJECT-TYPE
            SYNTAX  Counter64
            MAX-ACCESS read-only
            STATUS current
            DESCRIPTION
            " This object indicates the number of matched bytes. "    
            ::= { hwXQoSQppbGlobalStatisticsEntry 6 } 

      hwXQoSQppbGlobalStatisticsPassedPackets OBJECT-TYPE
            SYNTAX  Counter64
            MAX-ACCESS read-only
            STATUS current
            DESCRIPTION
            " This object indicates the number of passed packets. "    
            ::= { hwXQoSQppbGlobalStatisticsEntry 7 } 

      hwXQoSQppbGlobalStatisticsPassedBytes OBJECT-TYPE
            SYNTAX  Counter64
            MAX-ACCESS read-only
            STATUS current
            DESCRIPTION
            " This object indicates the number of passed bytes. "    
            ::= { hwXQoSQppbGlobalStatisticsEntry 8 } 

      hwXQoSQppbGlobalStatisticsDropedPackets OBJECT-TYPE
            SYNTAX  Counter64
            MAX-ACCESS read-only
            STATUS current
            DESCRIPTION
            " This object indicates the number of droped packets. "    
            ::= { hwXQoSQppbGlobalStatisticsEntry 9 }  

      hwXQoSQppbGlobalStatisticsDropedBytes OBJECT-TYPE
            SYNTAX  Counter64
            MAX-ACCESS read-only
            STATUS current
            DESCRIPTION
            " This object indicates the number of droped bytes. "     
            ::= { hwXQoSQppbGlobalStatisticsEntry 10 }

      hwXQoSQppbGlobalStatisticsMatchPacketsRate OBJECT-TYPE
            SYNTAX  Counter64
            MAX-ACCESS read-only
            STATUS current
            DESCRIPTION
            " This object indicates the rate of matched packets. "    
            ::= { hwXQoSQppbGlobalStatisticsEntry 11 }  

      hwXQoSQppbGlobalStatisticsMatchBytesRate OBJECT-TYPE
            SYNTAX  Counter64
            MAX-ACCESS read-only
            STATUS current
            DESCRIPTION
            " This object indicates the rate of matched bytes. "     
            ::= { hwXQoSQppbGlobalStatisticsEntry 12 }
        
 
      --   Beg add by w00176838 for remark payload-dscp
    hwXQoSCompliances  OBJECT IDENTIFIER ::=   { hwXQoSConformance 1 }
    hwXQoSGroups       OBJECT IDENTIFIER ::=   { hwXQoSConformance 2 }
    
    -- compliance statements

    hwXQoSCompliance MODULE-COMPLIANCE
        STATUS      current
        DESCRIPTION
        "The compliance statement for entities that implement 
        extend QoS on a router."
    
        MODULE -- this module
        MANDATORY-GROUPS { 
        hwXQoSIfQueueGroup,
        hwXQoSIfCarStatisticsGroup,
        hwXQoSCpDefendStatisticsGroup,
        hwNotificationExtGroup,
        hwXQosAtmTrafficQueueGroup,
        hwXQosAtmPvcServiceTypeGroup,
        hwXQosIfOutboundQueueStatisticGroup,
        hwXQoSBaGroup,
        hwXQoSBa8021pPhbGroup,
        hwXQoSBa8021pMapGroup,
        hwXQoSBaDscpPhbGroup,
        hwXQoSBaDscpMapGroup,
        hwXQoSBaExpPhbGroup,
        hwXQoSBaExpMapGroup,
        hwXQoSIfDiffDomainGroup,
        hwXQoSIfTrust8021pGroup,
        hwXQoSCommonInboundGroup,
        hwXQoSPppInboundGroup,
        hwXQoSServiceclassGroup,
        hwXQoSPhbGroup,
        hwXQoSFieldDeiGroup,
        hwXQoSPicForwardingGroup,
        hwXQoSCarTableGroup,
        hwXQoSPortShapingGroup,
        hwXQoSQueueGroup,
        hwXQoSCarStatisticsGroup,
        hwXQoSCpRateLimitGroup}
        ::= { hwXQoSCompliances 1 }      
    
    -- units of conformance
    
    hwXQoSIfQueueGroup OBJECT-GROUP
        OBJECTS {
        hwXQoSIfQueueIfIndex,
        hwXQoSIfQueueVlanID,
        hwXQoSIfQueueCosType,
        hwXQoSIfQueuePassedPackets,
        hwXQoSIfQueuePassededBytes,
        hwXQoSIfQueueTotalPackets,
        hwXQoSIfQueueTotalBytes,
        hwXQoSIfQueueDiscardedPackets,
        hwXQoSIfQueueDiscardedBytes,
        hwXQoSIfQueuePassedPacketRate,
        hwXQoSIfQueuePassedByteRate,
        hwXQoSIfQueueDiscardedPacketRate,
        hwXQoSIfQueueDiscardedByteRate,
        hwXQoSIfQueueResetFlag,  
        hwXQoSIfQueueUsagePercentage,
-- BEGIN: Added by l00248629, 2013/12/13
        hwXQoSIfQueueDropTailDiscardedPackets,
        hwXQoSIfQueueDropTailDiscardedBytes,
        hwXQoSIfQueueWredDiscardedPackets,
        hwXQoSIfQueueWredDiscardedBytes,
        hwXQoSIfQueueDropTailDiscardedPacketRate,
        hwXQoSIfQueueDropTailDiscardedByteRate,
        hwXQoSIfQueueWredDiscardedPacketRate,
        hwXQoSIfQueueWredDiscardedByteRate,    
        hwXQoSIfQueueStatisticsTrafficTowardThisPort,
        hwXQoSIfQueueStatisticsPhysicalBandwidthOfPortQoS
-- END: Added by l00248629, 2013/12/13                                                 
        }
        STATUS      current
        DESCRIPTION
        "This is a optional group of information."
        ::= { hwXQoSGroups 1 }

    hwXQoSIfCarStatisticsGroup OBJECT-GROUP
        OBJECTS {
        hwXQoSIfCarConformedPackets,
        hwXQoSIfCarConformedBytes,
        hwXQoSIfCarConformedPacketRate,
        hwXQoSIfCarConformedByteRate,
        hwXQoSIfCarExceededPackets,
        hwXQoSIfCarExceededBytes,
        hwXQoSIfCarExceededPacketRate,
        hwXQoSIfCarExceededByteRate,
        hwXQoSIfCarOverflowPackets,
        hwXQoSIfCarOverflowBytes,
        hwXQoSIfCarOverflowPacketRate,
        hwXQoSIfCarOverflowByteRate,
        hwXQoSIfCarPassedPackets,
        hwXQoSIfCarPassedBytes,
        hwXQoSIfCarDiscardedPackets,
        hwXQoSIfCarDiscardedBytes       
        }
        STATUS      current
        DESCRIPTION
        "This is a optional group of information."
        ::= { hwXQoSGroups 2 }        

    hwXQoSCpDefendStatisticsGroup OBJECT-GROUP
        OBJECTS {
        hwXQoSCpDefendSlotId,
        hwXQoSCpDefendObjectIndex,
        hwXQoSCpDefendPassedPackets,
        hwXQoSCpDefendPassedBytes,
        hwXQoSCpDefendPassedPacketRate,
        hwXQoSCpDefendPassedByteRate,
        hwXQoSCpDefendDiscardedPackets,
        hwXQoSCpDefendDiscardedBytes,
        hwXQoSCpDefendDiscardedPacketRate,
        hwXQoSCpDefendDiscardedByteRate,
        hwXQoSCpDefendDiscardedThreshold,
        hwXQoSCpDefendChassisID        
        }
        STATUS      current
        DESCRIPTION
        "This is a optional group of information."
        ::= { hwXQoSGroups 3 }

    hwNotificationExtGroup NOTIFICATION-GROUP
        NOTIFICATIONS { 
        hwXQoSCpDefendDiscardedRateAlarm,
        hwXQoSCpDefendDiscardedPacketAlarm,
        hwXQoSQueueDiscardThresholdTrap,
        hwXQoSStormControlTrap,
        hwXQoSCprlDiscardedPacketAlarm, 
        hwXQoSCprlDiscardedPacketAlarmClear,
        hwXQoSRedirectNextHopChangedAlarm,
        hwXQoSSecurityStormControlInterfaceTrap,
        hwXQoSIrsmDelayAlarm,
        hwXQoSIrsmSynFrameDropAlarm,
        hwXQoSStatResouceNotEnoughAlarm,
        hwXQoSIrsmDropPacketAlarm,
        hwXQoSRuleFaileAlarm,
        hwXQoSCpDefendDiscardedPacketAlarmClear,
        hwXQoSCARResouceNotEnoughAlarm,
        hwXQoSPortQueueAlarmClear,
        hwXQoSProfileUsedAlarm,
        hwXQoSPortQueueAlarm 
        }
        STATUS  current
        DESCRIPTION
            "The HUAWEI defend trap info."
        ::= { hwXQoSGroups 4 }    
        
    hwXQoSGeneralGroup OBJECT-GROUP
        OBJECTS {
        hwXQoSFrameId, 
        hwXQoSSlotId, 
        hwXQoSPortId, 
        hwXQoSTrapIfName,    
        hwXQoSTrapQueueId,
        hwXQoSTrapDiscardPackets
        }
        STATUS  current
        DESCRIPTION
        "This is a optional group of information."
        ::= { hwXQoSGroups 5 }
        
    hwXQoSSredGroup OBJECT-GROUP
        OBJECTS {
        hwXQoSIfSredQueueIndex,
        hwXQoSIfSredRedStartDiscardPoint,
        hwXQoSIfSredRedDiscardProbability,                           
        hwXQoSIfSredYellowStartDiscardPoint,
        hwXQoSIfSredYellowDiscardProbability,
        hwXQoSIfSredRowStatus
        }
        STATUS  current
        DESCRIPTION
        "This is Sred group of information."
        ::= { hwXQoSGroups 6 } 
        
      hwXQosAtmTrafficQueueGroup OBJECT-GROUP
      OBJECTS { 
      hwXQoSAtmTrafficQueueServiceClass, 
      hwXQoSAtmTrafficQueueRowStatus 
      }
      STATUS current
      DESCRIPTION 
          "This is a optional group of information."
      ::= { hwXQoSGroups 7 }
      hwXQosAtmPvcServiceTypeGroup OBJECT-GROUP
      OBJECTS { 
      hwXQoSAtmPvcNameServiceTypeIndex, 
      hwXQoSAtmPvcServiceType, 
      hwXQoSAtmPvcPcr, 
      hwXQoSAtmPvcCdvt, 
      hwXQoSAtmPvcVbrScr, 
      hwXQoSAtmPvcVbrMbs,
      hwXQoSAtmPvcRowStatus 
      }
      STATUS current
      DESCRIPTION 
         "This is a optional group of information."
      ::= { hwXQoSGroups 8 }
         
     hwXQosIfOutboundQueueStatisticGroup OBJECT-GROUP
     OBJECTS { 
     hwXQoSIfQueDiscardPackets 
     }
     STATUS current
     DESCRIPTION 
         "This is a optional group of information."
     ::= { hwXQoSGroups 9 }
      
     hwXQoSShapingGroup OBJECT-GROUP
        OBJECTS {
            hwXQoSIfShapingIfIndex,
            hwXQoSIfShapingQueueIndex, 
            hwXQoSIfShapingQueueCir,
            hwXQoSIfShapingQueuePir,
            hwXQoSIfShapingRowStatus
        }
        STATUS  current
        DESCRIPTION
        "This is Shaping group of information."
        ::= { hwXQoSGroups 10 } 


     hwXQoSUrpfDiscardStatisticsGroup OBJECT-GROUP
        OBJECTS {        
               hwXQoSUrpfSlotPhysicalIndex,
       hwXQoSUrpfDiscardedPackets                
        }
        STATUS  current
        DESCRIPTION
        "This is a optional group of information."
        ::= { hwXQoSGroups 11 } 



        hwXQoSBaGroup OBJECT-GROUP
            OBJECTS { hwXQoSBaIndex, hwXQoSBaName, hwXQoSBaRowStatus }
            STATUS current
            DESCRIPTION 
                "This is different server domain  group of information."
            ::= { hwXQoSGroups 12 }

        
        hwXQoSBa8021pPhbGroup OBJECT-GROUP
            OBJECTS { hwXQoSBa8021pPhbIndex, hwXQoSBa8021pPhbPri, hwXQoSBa8021pPhbCos, hwXQoSBa8021pPhbColour, hwXQoSBa8021pPhbRowStatus
                 }
            STATUS current
            DESCRIPTION 
                "This is different server domain  group of information."
            ::= { hwXQoSGroups 13 }

        
        hwXQoSBa8021pMapGroup OBJECT-GROUP
            OBJECTS { hwXQoSBa8021pMapIndex, hwXQoSBa8021pMapCos, hwXQoSBa8021pMapColour, hwXQoSBa8021pMapPri, hwXQoSBa8021pMapRowStatus
                 }
            STATUS current
            DESCRIPTION 
                "This is different server domain  group of information."
            ::= { hwXQoSGroups 14 }

        
        hwXQoSBaDscpPhbGroup OBJECT-GROUP
            OBJECTS { hwXQoSBaDscpPhbIndex, hwXQoSBaDscpPhbPri, hwXQoSBaDscpPhbCos, hwXQoSBaDscpPhbColour, hwXQoSBaDscpPhbRowStatus
                 }
            STATUS current
            DESCRIPTION 
                "This is different server domain  group of information."
            ::= { hwXQoSGroups 15 }

        
        hwXQoSBaDscpMapGroup OBJECT-GROUP
            OBJECTS { hwXQoSBaDscpMapIndex, hwXQoSBaDscpMapCos, hwXQoSBaDscpMapColour, hwXQoSBaDscpMapPri, hwXQoSBaDscpMapRowStatus
                 }
            STATUS current
            DESCRIPTION 
                "This is different server domain  group of information."
            ::= { hwXQoSGroups 16 }

        
        hwXQoSBaExpPhbGroup OBJECT-GROUP
            OBJECTS { hwXQoSBaExpPhbIndex, hwXQoSBaExpPhbPri, hwXQoSBaExpPhbCos, hwXQoSBaExpPhbColour, hwXQoSBaExpPhbRowStatus
                 }
            STATUS current
            DESCRIPTION 
                "This is different server domain  group of information."
            ::= { hwXQoSGroups 17 }

        
        hwXQoSBaExpMapGroup OBJECT-GROUP
            OBJECTS { hwXQoSBaExpMapIndex, hwXQoSBaExpMapCos, hwXQoSBaExpMapColour, hwXQoSBaExpMapPri, hwXQoSBaExpMapRowStatus
                 }
            STATUS current
            DESCRIPTION 
                "This is different server domain  group of information."
            ::= { hwXQoSGroups 18 }

        
        hwXQoSIfDiffDomainGroup OBJECT-GROUP
            OBJECTS { hwXQoSIfDiffDomainIfIndex, hwXQoSIfDiffDomainVlanId, hwXQoSIfDiffDomainName, hwXQoSIfDiffDomainRowStatus, hwXQoSIfDiffDomainVlanId2
                 }
            STATUS current
            DESCRIPTION 
                "This is different server domain  group of information."
            ::= { hwXQoSGroups 19 }

        
        hwXQoSBaPhbGroup OBJECT-GROUP
            OBJECTS { hwXQoSBaPhbType, hwXQoSBaPhbPri, hwXQoSBaPhbCos, hwXQoSBaPhbColour, hwXQoSBaPhbRowStatus
                 }
            STATUS current
            DESCRIPTION 
                "This is different server domain  group of information."
            ::= { hwXQoSGroups 20 }

        
        hwXQoSBaMapGroup OBJECT-GROUP
            OBJECTS { hwXQoSBaMapType, hwXQoSBaMapCos, hwXQoSBaMapColour, hwXQoSBaMapPri, hwXQoSBaMapRowStatus
                 }
            STATUS current
            DESCRIPTION 
                "This is different server domain  group of information."
            ::= { hwXQoSGroups 21 }

        hwXQoSIfTrustGroup OBJECT-GROUP
            OBJECTS { hwXQoSIfTrustIfIndex, hwXQoSIfTrustVlanID1, hwXQoSIfTrustVlanID2, hwXQoSBaType, hwXQoSIfTrustAction, 
                hwXQoSIfTrustRowStatus}
            STATUS current
            DESCRIPTION 
                "This is different server domain  group of information."
            ::= { hwXQoSGroups 22 }

        
        hwXQosVlanStatGroup OBJECT-GROUP
            OBJECTS {hwXQosVlanStatInTotalPkts, hwXQosVlanStatInTotalBytes, hwXQosVlanStatOutTotalPkts, hwXQosVlanStatOutTotalBytes, 
                hwXQosVlanStatInUcastPkts, hwXQosVlanStatInUcastBytes, hwXQosVlanStatOutUcastPkts, hwXQosVlanStatOutUcastBytes, hwXQosVlanStatInMcastPkts, 
                hwXQosVlanStatInMcastBytes, hwXQosVlanStatOutMcastPkts, hwXQosVlanStatOutMcastBytes, hwXQosVlanStatInBcastPkts, hwXQosVlanStatInBcastBytes, 
                hwXQosVlanStatOutBcastPkts, hwXQosVlanStatOutBcastBytes, hwXQosVlanStatInUnknownUcastPkts, hwXQosVlanStatInUnknownUcastBytes, hwXQosVlanStatResetFlag
                 }
            STATUS current
            DESCRIPTION 
                "This is statistic group of information."
            ::= { hwXQoSGroups 23 }

        
        hwXQoSVlanCfgGroup OBJECT-GROUP
            OBJECTS { hwXQoSVlanStatEnable }
            STATUS current
            DESCRIPTION 
                "This is statistic group of information."
            ::= { hwXQoSGroups 24 }

     hwXQoSStormControlGroup OBJECT-GROUP
         OBJECTS {
             hwXQoSStormControlBroadcastMinRate,
             hwXQoSStormControlBroadcastMaxRate, 
             hwXQoSStormControlMulticastMinRate, 
             hwXQoSStormControlMulticastMaxRate, 
             hwXQoSStormControlAction, 
             hwXQoSStormControlInterval, 
             hwXQoSStormControlTrapEnable,             
             hwXQoSStormControlLogEnable,
             hwXQoSStormControlStatus,
            hwXQoSStormControlUnicastMinRate,
             hwXQoSStormControlUnicastMaxRate,
             hwXQoSStormControlBcMode,
             hwXQoSStormControlMcMode,
             hwXQoSStormControlUcMode                                     
         }
    STATUS current
    DESCRIPTION 
    "This is shaping group of information."
    ::= { hwXQoSGroups 25 }
    hwXQoSQueueStatisticsGroup OBJECT-GROUP
        OBJECTS {
            hwXQoSQueueStatisticsPassedPacketsCount,
            hwXQosQueueStatisticsReset,
            hwXQoSQueueStatisticsRowStatus               
        }
        STATUS current
        DESCRIPTION 
                "This is shaping group of information."
        ::= { hwXQoSGroups 26}

    hwXQoSIfPppoeGroup OBJECT-GROUP
        OBJECTS { 
            hwXQoSIfPppoeRowStatus
        }
        STATUS current
        DESCRIPTION 
            "This is PPPoE group of information."
        ::= { hwXQoSGroups 27 }

    hwXQoSVlanBcastSuppressGroup OBJECT-GROUP
        OBJECTS { 
            hwXQoSVlanBcastSuppressValue, 
            hwXQoSVlanBcastSuppressRowStatus 
        }
        STATUS current
        DESCRIPTION 
            "This is VLAN broadcast suppression group of information."
        ::= { hwXQoSGroups 28 }

         hwXQoSRedirectNextHopGroup OBJECT-GROUP
                  OBJECTS {
                        hwXQoSRedirectNextHopBehaviorName,
                        hwXQoSRedirectNextHopOldIp,
                        hwXQoSRedirectNextHopNewIp
                          }
                     STATUS  current
                     DESCRIPTION
                                 "This is the redirect next hop group of information."
                     ::= { hwXQoSGroups 29 } 


        hwXQoSIfTrust8021pGroup OBJECT-GROUP
            OBJECTS { 
                hwXQoSIfTrust8021pIfIndex,
                hwXQoSIfTrust8021pVlanID,
                hwXQoSIfTrust8021pAction,
                hwXQoSIfTrust8021pRowStatus        
            }
            STATUS current
            DESCRIPTION 
                "Description."
            ::= { hwXQoSGroups 30} 

        hwXQoSCommonInboundGroup OBJECT-GROUP
          OBJECTS{
                hwXQoSCommonInboundPhbIndex     ,
                hwXQoSCommonInboundPhbCos   ,
                hwXQoSCommonInboundPhbColor      ,
                hwXQoSCommonInboundPhbPri     ,
                hwXQoSCommonInboundRowStatus                                         
                 }
          STATUS current       
          DESCRIPTION 
              " hwXQoSCommonInboundGroup "
          ::= { hwXQoSGroups 31 }  


            
        hwXQoSPppInboundGroup OBJECT-GROUP
          OBJECTS{
                hwXQoSPppInboundCos,
                hwXQoSPppInboundColor,
                hwXQoSPppInboundRowStatus                                        
                 }
          STATUS current       
          DESCRIPTION 
              " hwXQoSPppInboundGroup "
          ::= { hwXQoSGroups 32 } 
        


        hwXQoSServiceclassGroup OBJECT-GROUP
          OBJECTS{
                hwXQoSServiceclassPort     ,
                hwXQoSServiceclass   ,
                hwXQoSServiceclassRowStatus                                        
                 }
          STATUS current       
          DESCRIPTION 
              " hwXQoSServiceclassGroup "
          ::= { hwXQoSGroups 33 } 
            
            
                      
      hwXQoSPhbGroup OBJECT-GROUP
          OBJECTS{
                hwXQoSPhbPort     ,
                hwXQoSPhbEnable,
                hwXQoSPhbRowStatus                                
                 }
          STATUS current       
          DESCRIPTION 
              " hwXQoSPhbGroup "
          ::= { hwXQoSGroups 34 }    

       hwXQoSFieldDeiGroup OBJECT-GROUP
          OBJECTS{
                hwXQoSFieldDeiInterface,
                hwXQoSFieldDeiVlanId,  
                hwXQoSFieldDeiEnabled,
                hwXQoSFieldDeiRowStatus                                
                 }
          STATUS current       
          DESCRIPTION 
              " hwXQoSFieldDeiGroup "
          ::= { hwXQoSGroups 35 }   

       hwXQoSPicForwardingGroup OBJECT-GROUP
          OBJECTS{
                hwXQoSPicForwardingInterface,
                hwXQoSPicForwarding8021pValue,
                hwXQoSPicForwardingPriority,
                hwXQoSPicForwardingRowStatus                               
                 }
          STATUS current       
          DESCRIPTION 
              " hwXQoSPicForwardingGroup "
          ::= { hwXQoSGroups 36 }



       hwXQoSCarTableGroup OBJECT-GROUP
          OBJECTS{
                hwXQoSCarInterfaceIndex,  
                hwXQoSCarDirection,
                hwXQoSCarVlanID,
                hwXQoSCarCirValue,
                hwXQoSCarPirValue,
                hwXQoSCarCbsValue,
                hwXQoSCarPbsValue,
                hwXQoSCarGreenAction,
                hwXQoSCarGreenServiceClass,
                hwXQoSCarGreenColor,
                hwXQoSCarYellowAction,
                hwXQoSCarYellowServiceClass,
                hwXQoSCarYellowColor,
                hwXQoSCarRedAction,
                hwXQoSCarRedServiceClass,
                hwXQoSCarRedColor,            
                hwXQoSCarRowStatus                               
                 }
          STATUS current       
          DESCRIPTION 
              " hwXQoSCarTableGroup "
          ::= { hwXQoSGroups 37 }



       hwXQoSPortShapingGroup OBJECT-GROUP
          OBJECTS{
                hwXQoSPortShapingInterface,
                hwXQoSPortShapingValue,
                hwXQoSPortShapingPbsValue,
                hwXQoSPortShapingRowStatus                               
                 }
          STATUS current       
          DESCRIPTION 
              " hwXQoSPortShapingGroup "
          ::= { hwXQoSGroups 38 }



       hwXQoSQueueGroup OBJECT-GROUP
          OBJECTS{
                hwXQoSQueueInterfaceIndex,
                hwXQoSQueueServiceClass,
                hwXQoSQueueCirValue,
                hwXQoSQueueCirPercentage,
                hwXQoSQueueDirection,
                hwXQoSQueueRowStatus                               
                 }
          STATUS current       
          DESCRIPTION 
              " hwXQoSQueueGroup "
          ::= { hwXQoSGroups 39 }



       hwXQoSCarStatisticsGroup OBJECT-GROUP
          OBJECTS{
                hwXQoSCarStatisticsInterfaceIndex,
                hwXQoSCarStatisticsDirection,
                hwXQoSCarStatisticsVlanid,
                hwXQoSCarStatisticsSlotNumber,
                hwXQoSCarStatisticsReset,
                hwXQoSCarStatisticsPassPackets,
                hwXQoSCarStatisticsPassBytes,
                hwXQoSCarStatisticsDropPackets,
                hwXQoSCarStatisticsDropBytes,
                hwXQoSCarStatisticsPassPacketsRate,
                hwXQoSCarStatisticsPassBytesRate,
                hwXQoSCarStatisticsDropPacketsRate,
                hwXQoSCarStatisticsDropBytesRate                               
                 }
          STATUS current       
          DESCRIPTION 
              " hwXQoSCarStatisticsGroup "
          ::= { hwXQoSGroups 40 }



       hwXQoSCpRateLimitGroup OBJECT-GROUP
          OBJECTS{
                hwXQoSCpRateLimitIfIndex,
                hwXQoSCpRateLimitPeVidValue,
                hwXQoSCpRateLimitCeVidBegin,
                hwXQoSCpRateLimitCeVidEnd,
                hwXQoSCpRateLimitType,
                hwXQoSCpRateLimitIgmpCir,
                hwXQoSCpRateLimitIgmpCbs,
                hwXQoSCpRateLimitRowStatus                               
                 }
          STATUS current       
          DESCRIPTION 
              " hwXQoSCpRateLimitGroup "
          ::= { hwXQoSGroups 41 }

       hwXQoSPortQueueStatisticsGroup OBJECT-GROUP
            OBJECTS {hwXQoSPortQueueStatisticsInterfaceIndex,hwXQoSPortQueueStatisticsDirection,
            hwXQoSPortQueueStatisticsQueueIndex,hwXQoSPortQueueStatisticsReset,
            hwXQoSPortQueueStatisticsTotalPassPackets,hwXQoSPortQueueStatisticsTotalPassBytes,
            hwXQoSPortQueueStatisticsTotalDiscardPackets,hwXQoSPortQueueStatisticsTotalDiscardBytes,
            hwXQoSPortQueueStatisticsDropTailDiscardPackets,hwXQoSPortQueueStatisticsDropTailDiscardBytes,
            hwXQoSPortQueueStatisticsWredDiscardPackets,hwXQoSPortQueueStatisticsWredDiscardBytes,
            hwXQoSPortQueueStatisticsPassPacketsRate,hwXQoSPortQueueStatisticsPassBytesRate,
            hwXQoSPortQueueStatisticsDiscardPacketsRate,hwXQoSPortQueueStatisticsDiscardBytesRate,
            hwXQoSPortQueueStatisticsDropTailDiscardPacketsRate,hwXQoSPortQueueStatisticsDropTailDiscardBytesRate,
            hwXQoSPortQueueStatisticsWredDiscardPacketsRate,hwXQoSPortQueueStatisticsWredDiscardBytesRate,  
-- BEGIN: Added by l00248629, 2013/12/13
            hwXQoSPortQueueStatisticsTrafficTowardThisPort,hwXQoSPortQueueStatisticsPhysicalBandwidthOfPortQoS,
-- END: Added by l00248629, 2013/12/13                                                 
            hwXQoSPortQueueStatisticsQueuePercentage,    
-- BEGIN: Added by l00248629, 2013/12/13
            hwXQoSPortQueueStatisticsTotalPackets,hwXQoSPortQueueStatisticsTotalBytes
-- END: Added by l00248629, 2013/12/13                                                 
            }
            STATUS current
            DESCRIPTION 
                "Description."
            ::= { hwXQoSGroups 42 }   
      
        hwXQoSPortStatisticsDropGroup OBJECT-GROUP
        OBJECTS {
            hwXQoSPortStatisticsDropPacketsCount,
            hwXQosPortStatisticsDropReset,
            hwXQosPortStatisticsDropResetTime             
        }
        STATUS current
        DESCRIPTION 
                "This is the drop packets statistics of port group of information."
        ::= { hwXQoSGroups 43}    
        
        
        hwXQoSQueueStatisticsDropGroup OBJECT-GROUP
        OBJECTS {
            hwXQoSQueueStatisticsDropPacketsCount,
            hwXQosQueueStatisticsDropReset,
            hwXQosQueueStatisticsDropResetTime                     
        }
        STATUS current
        DESCRIPTION 
                "This is the drop packets statistics of queue group of information."

        ::= { hwXQoSGroups 44}

    hwXQoSIfScheduleGroup OBJECT-GROUP
        OBJECTS {  
            hwXQoSIfScheduleProfile, 
            hwXQoSIfScheduleRowStatus
        }
        STATUS current
        DESCRIPTION 
            "This is Interface schedule group of information."
        ::= { hwXQoSGroups 45 }
      
    hwXQoSScheduleProfileGroup OBJECT-GROUP
        OBJECTS { 
            hwXQoSScheduleQueueMode, 
            hwXQoSScheduleQueueBeWeight,
            hwXQoSScheduleQueueAf1Weight,
            hwXQoSScheduleQueueAf2Weight,
            hwXQoSScheduleQueueAf3Weight,
            hwXQoSScheduleQueueAf4Weight,
            hwXQoSScheduleQueueCs6Weight,
            hwXQoSScheduleQueueCs7Weight,
            hwXQoSScheduleQueueEfWeight,
            hwXQoSScheduleProfileRowStatus
        }
        STATUS current
        DESCRIPTION 
            "This is schedule profile group of information."
        ::= { hwXQoSGroups 46 }            
                                        
  --w00164261
    hwXQoSQppbPolicyGroup OBJECT-GROUP
        OBJECTS {
             hwXQoSQppbPolicyStatisticsInterfaceIndex,                 
             hwXQoSQppbPolicyDirection,  
             hwXQoSQppbPolicyLocalID,  
             hwXQoSQppbPolicyStatisticsReset,  
             hwXQoSQppbPolicyMatchedPackets, 
             hwXQoSQppbPolicyMatchedBytes,
             hwXQoSQppbPolicyPassedPackets, 
             hwXQoSQppbPolicyPassedBytes,    
             hwXQoSQppbPolicyDropedPackets,
             hwXQoSQppbPolicyDropedBytes
        }
        STATUS current
        DESCRIPTION 
            "Description."
        ::= { hwXQoSGroups 47 }
        
        --begin add by wangyonggui 176838, CAR/STAT Alarm    
        hwXQoSStatResouceNotEnoughAlarmGroup OBJECT-GROUP
            OBJECTS { hwXQoSStatResouceNotEnoughSlotId, hwXQoSStatResouceNotEnoughStatType }
            STATUS current
            DESCRIPTION 
                "Description."
            ::= { hwXQoSGroups 48 }
            
        hwXQoSCARResouceNotEnoughAlarmGroup OBJECT-GROUP
            OBJECTS { hwXQoSCARResouceNotEnoughSlotId, hwXQoSCARResouceNotEnoughCARType }
            STATUS current
            DESCRIPTION 
                "Description."
            ::= { hwXQoSGroups 49 }    
        --end add by wangyonggui 176838, CAR/STAT Alarm  
        
        hwXQoSSecurityStormControlInterfaceObjects OBJECT IDENTIFIER ::= { hwXQoSObjects 21 }

        hwXQoSSecurityStormControlInterfaceTable OBJECT-TYPE
            SYNTAX SEQUENCE OF HwXQoSSecurityStormControlInterfaceEntry
            MAX-ACCESS not-accessible
            STATUS current
            DESCRIPTION
                "A Table about storm-control interface information."
            ::= { hwXQoSSecurityStormControlInterfaceObjects 1 }

        
        hwXQoSSecurityStormControlInterfaceEntry OBJECT-TYPE
            SYNTAX HwXQoSSecurityStormControlInterfaceEntry
            MAX-ACCESS not-accessible
            STATUS current
            DESCRIPTION
                "Description."
            INDEX { hwXQoSSecurityStormControlInterfaceChassisId,
                    hwXQoSSecurityStormControlInterfaceSlotId
                  }
            ::= { hwXQoSSecurityStormControlInterfaceTable 1 }

        
        HwXQoSSecurityStormControlInterfaceEntry ::=
            SEQUENCE {
                hwXQoSSecurityStormControlInterfaceChassisId
                    Integer32,
                hwXQoSSecurityStormControlInterfaceSlotId
                    Integer32,
                hwXQoSSecurityStormControlInterfaceName   
                    OCTET STRING,
                hwXQoSSecurityStormControlInterfaceVlan
                    Integer32          
             }
 
         hwXQoSSecurityStormControlInterfaceChassisId OBJECT-TYPE
            SYNTAX Integer32 (1..128)
            MAX-ACCESS read-only
            STATUS current
            DESCRIPTION
                "The chassis ID indicates the slot on which chassis is configured with storm control."
            ::= { hwXQoSSecurityStormControlInterfaceEntry 1 }
            
         hwXQoSSecurityStormControlInterfaceSlotId OBJECT-TYPE
            SYNTAX Integer32 (1..128)
            MAX-ACCESS read-only
            STATUS current
            DESCRIPTION
                "The slot configured with storm control."
            ::= { hwXQoSSecurityStormControlInterfaceEntry 2 }

        hwXQoSSecurityStormControlInterfaceName OBJECT-TYPE
            SYNTAX OCTET STRING (SIZE (0..63))
            MAX-ACCESS read-only
            STATUS current
            DESCRIPTION
                "The interface name."
            ::= { hwXQoSSecurityStormControlInterfaceEntry 3 }                                  
        
        hwXQoSSecurityStormControlInterfaceVlan OBJECT-TYPE
            SYNTAX Integer32 (0..4095)
            MAX-ACCESS read-only
            STATUS current
            DESCRIPTION
                "The value of this object identifies the VLAN ID of the interface."
            ::= { hwXQoSSecurityStormControlInterfaceEntry 4 }
       
-- BEGIN: Added by w00218179, 2013/6/13            
        -- 1.3.6.1.4.1.2011.5.25.32.4.2.2.50
		hwXQosCarResourceGroup OBJECT-GROUP
			OBJECTS { hwXQosCarResourceDirection, hwXQosCarResourceSlotNumber, hwXQosCarResourceServiceType, hwXQosCarResourceTotalValue, hwXQosCarResourceAllocatedValue, hwXQosCarResourceFreeValue }
			STATUS current
			DESCRIPTION 
			"This is CAR Resource group of information."
			::= { hwXQoSGroups 50 }  
-- END: Added by w00218179, 2013/6/13                                                 
    END

--
-- HUAWEI-XQoS-MIB.mib
--
