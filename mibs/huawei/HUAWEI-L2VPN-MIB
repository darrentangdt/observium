-- HUAWEI-L2VPN-MIB.mib
--  ==================================================================
-- Copyright (C) 2009 by  HUAWEI TECHNOLOGIES. All rights reserved.
-- 
-- Description: HUAWEI L2VPN Management MIB
-- Reference:
-- Version:     V1.0
-- History:
--              V1.0 WangSongTao, 2009-02-26, publish
-- ==================================================================
    
    HUAWEI-L2VPN-MIB DEFINITIONS ::= BEGIN
    
        IMPORTS
            hwDatacomm           
                FROM HUAWEI-MIB
                    EnabledStatus
                FROM P-BRIDGE-MIB
                    OBJECT-GROUP, MODULE-COMPLIANCE
                FROM SNMPv2-CONF                 
                    sysUpTime         
                FROM SNMPv2-MIB
                    OBJECT-TYPE, MODULE-IDENTITY
                FROM SNMPv2-SMI;
        
        -- 1.3.6.1.4.1.2011.5.25.119.8
            hwL2VpnAttribute MODULE-IDENTITY 
                LAST-UPDATED "200903030900Z"                -- March 03, 2009 at 09:00 GMT
                ORGANIZATION
                     "Huawei Technologies Co.,Ltd."
                CONTACT-INFO 
                     "Huawei Industrial Base
                       Bantian, Longgang
                        Shenzhen 518129
                        People's Republic of China
                        Website: http://www.huawei.com
                        Email: support@huawei.com
                      "
                DESCRIPTION
                     "The HUAWEI-L2VPN-MIB contains objects to
                      manage global Attributes of L2VPN."
                ::= { hwL2Vpn 8 }
                
-- 
-- Node definitions
-- 
  
        -- 1.3.6.1.4.1.2011.5.25.119
        hwL2Vpn OBJECT IDENTIFIER ::= { hwDatacomm 119 }
                
--         
-- The Global Attributes Group of The mpls L2vpn
-- 
  
-- 
-- The Leaf Nodes of hwL2VpnAttribute
-- 
        -- 1.3.6.1.4.1.2011.5.25.119.8.1
        hwL2VpnEnable OBJECT-TYPE
            SYNTAX EnabledStatus
            MAX-ACCESS read-write
            STATUS current
            DESCRIPTION
                "This object indicates whether enabled mpls L2vpn capability or not."
            ::= { hwL2VpnAttribute 1 }                
            
        -- 1.3.6.1.4.1.2011.5.25.119.8.2
        hwL2VpnWorkingMode OBJECT-TYPE
            SYNTAX INTEGER
                {
                pwe3(1),
                martini(2),
                unknown(3)
                }
            MAX-ACCESS read-write
            STATUS current
            DESCRIPTION
                "This object indicates the working mode of mpls L2vpn."
            ::= { hwL2VpnAttribute 2 }
            
-- 
--  Conformance information
-- 
        -- 1.3.6.1.4.1.2011.5.25.119.8.3
        hwL2VpnMIBConformance OBJECT IDENTIFIER ::= { hwL2VpnAttribute 3 }
        
        -- 1.3.6.1.4.1.2011.5.25.119.8.3.1
        hwL2VpnMIBCompliances OBJECT IDENTIFIER ::= { hwL2VpnMIBConformance 1 }
        
-- this module
        -- 1.3.6.1.4.1.2011.5.25.119.8.3.1.1
        hwL2VpnMIBCompliance MODULE-COMPLIANCE
            STATUS current
            DESCRIPTION 
                "The compliance statement for systems supporting
                 the HUAWEI-L2VPN-MIB."
            MODULE -- this module
            MANDATORY-GROUPS { hwL2VpnMIBGroup }
            ::= { hwL2VpnMIBCompliances 1 }
        
        -- 1.3.6.1.4.1.2011.5.25.119.8.3.2
        hwL2VpnMIBGroups OBJECT IDENTIFIER ::= { hwL2VpnMIBConformance 2 }
        
        -- 1.3.6.1.4.1.2011.5.25.119.8.3.2.1
        hwL2VpnMIBGroup OBJECT-GROUP
            OBJECTS { hwL2VpnEnable, hwL2VpnWorkingMode }
            STATUS current
            DESCRIPTION 
                "The L2VPN's attributes group."
            ::= { hwL2VpnMIBGroups 1 }                
 
        END

--
-- HUAWEI-L2VPN-MIB.mib
--
