--
-- HUAWEI-FWD-RES-TRAP-MIB.mib
-- Copyright (C) 2006 by HUAWEI TECHNOLOGIES. All rights reserved
-- Thursday, June 24, 2010 at 15:26:04
--Version: V2.39

    HUAWEI-FWD-RES-TRAP-MIB DEFINITIONS ::= BEGIN
 
        IMPORTS
            entPhysicalName            
                FROM ENTITY-MIB            
            hwDatacomm            
                FROM HUAWEI-MIB            
            OBJECT-GROUP, MODULE-COMPLIANCE, NOTIFICATION-GROUP            
                FROM SNMPv2-CONF            
            Unsigned32, OBJECT-TYPE, MODULE-IDENTITY, NOTIFICATION-TYPE            
                FROM SNMPv2-SMI;
    
    
        hwFwdResTrapMIB MODULE-IDENTITY 
            LAST-UPDATED "201403051526Z"        -- March 05, 2014 at 15:26 GMT
            ORGANIZATION 
                "Huawei Technologies Co.,Ltd."
            CONTACT-INFO 
                "Huawei Industrial Base
                  Bantian, Longgang
                   Shenzhen 518129
                   People's Republic of China
                   Website: http://www.huawei.com
                   Email: support@huawei.com
                 "
           DESCRIPTION 
           "The private mib file includes the alarm  
           information of fowarding engine resouce overload."
 
            REVISION "201403051526Z"        --  March 05, 2014 at 15:26 GMT
            DESCRIPTION  
            "Add hwBoardIPv6ACLResLack  22."  
            
            REVISION "201401231657Z"        -- Jan 23, 2014 at 16:57 GMT 
            DESCRIPTION 
            " add reasonid     fwdInAc(168)   fwdOutAc(169)      fwdLem(170)      fwdL2Entry(171)        fwdMcMacfibv4(172)   fwdSnoop(173)   fwdArp(174) " 
            
            REVISION "201401211140Z"        -- Jan 21, 2014 at 11:40 GMT
            DESCRIPTION 
            " modified  hwBoardResWarningThresholdExceed,hwBoardResWarningThresholdExceedResume." 
                  
            REVISION "201401142146Z"        -- Jan 14, 2014 at 21:46 GMT
            DESCRIPTION 
            "Add  hwBoardResThresholdExceed,hwBoardResThresholdExceedResume,hwBoardResWarningThresholdExceed,hwBoardResWarningThresholdExceedResume." 
                           
           REVISION "201401061952Z"        -- Jan 06, 2014 at 19:52 GMT  
           DESCRIPTION  
           "Add QPPB alarm type."         
       
           REVISION "201312121728Z" -- Sep 12, 2013 at 17:28 GMT
           DESCRIPTION
            "Add Beavior alarm type."

            REVISION "201311131028Z"        -- Nov 13, 2013 at 10:28 GMT
            DESCRIPTION
            "Add hwFwdResLacTrap 17 "
 
           REVISION "201305141121Z" -- May 14, 2013 at 11:21 GMT
           DESCRIPTION
            "Add alarm type."
          
           REVISION "201305141121Z" -- May 14, 2013 at 11:21 GMT
           DESCRIPTION
            "Add alarm type."

            REVISION "201006041043Z"        -- June 04, 2010 at 10:43 GMT
            DESCRIPTION
                "ver 1.0"  
            ::= { hwDatacomm 227 }       
    
    
--
-- Node definitions
--
    
        -- 1.3.6.1.4.1.2011.5.25.227.1
        hwFwdResTrapObject OBJECT IDENTIFIER ::= { hwFwdResTrapMIB 1 }
        
        -- 1.3.6.1.4.1.2011.5.25.227.1.1
        hwEntPhysicalindex OBJECT-TYPE
            SYNTAX Unsigned32
            MAX-ACCESS accessible-for-notify
            STATUS current
            DESCRIPTION
                "The index for this entry."
            ::= { hwFwdResTrapObject 1 }
        
        -- 1.3.6.1.4.1.2011.5.25.227.1.2
        hwFwdResLackSlotStr OBJECT-TYPE
            SYNTAX OCTET STRING
            MAX-ACCESS accessible-for-notify
            STATUS current
            DESCRIPTION
                "The information for the slot."
            ::= { hwFwdResTrapObject 2 }
        
        -- 1.3.6.1.4.1.2011.5.25.227.1.3
        hwFwdResLackReasonId OBJECT-TYPE
            SYNTAX INTEGER
                {
                mplsLinkOverLoad(1),
                fibv4NumOverLoad(2),
                fibv6NumOverLoad(3),
                arpNumOverLoad(4),
                ipv6NdNumOverLoad(5),
                statNumOverLoad(6),
                qosNumOverLoad(7),
                l2vpnLinkOverLoad(8),
                mcintNumOverLoad(9),
                bfdaclNumOverLoad(10),
                mcfibv4NumOverLoad(11),
                mcfibv6NumOverLoad(12),
                fwdToken(13),
                fvrfIndex(14),
                ndIndex(15),
                tunnelIndex(16),
                bfdIndex(17),
                vplsLearnId(18),
                vsiIndex(19),
                nsIndex(20),
                ringIndex(21),
                mcRepSerNumOverload(22),
                mcOutIfNumOverload(23),
                mcTmgidOverLoad(24),                    
                mcMlidOverLoad(25),                       
                trillNhpIndex(26),                        
                hostTablePrefixTable(27),                  
                routingTablePrefixTable(28),               
                ecmpNextHopTable(29),             
                layer3InterfaceTable(30),                  
                nextHopTable(31),                 
                tunnelDecapsulationTable(32),              
                qvctNumOverload(33),                       
                bfdGlobalIndex(34),
                ipv4FullRull(35), 
                ipv4MaskRull(36), 
                ipv6FullRull(37),
                ipv6MaskRull(38),
                dpiRull(39),
                comRull(40),
                tcpFlagRull(41),
                ccSendNum(42),
                ccRecvNum(43),
                y1731SlmNum(44),
                y17311dmNum(45),
                y17312dmNum(46),
                ipv6RoutingTablePrefixTable(47),
                mcv4StatId(48),
                mcv6StatId(49),
                nhpNum(50),
                nscvmNum(51),
                y1731dlmNum(52), 
                bgpExtNum(53),
                bgp6ExtNum(54),
                linkEncap(55), 
                tunnelEncap(56), 
                largeExactlyMatchTable(57), 
                logicalInterface(58), 
                macMulticastIndex(59), 
                virtualPort(60), 
                aclEntry(61), 
                aclGroup(62), 
                meter(63), 
                counter(64), 
                aclEntryOutbound(65), 
                aclGroupOutbound(66), 
                meterOutbound(67), 
                counterOutbound(68), 
                multicastIndex(69), 
                ipfpmAclResOverLoad(70), 
                dhcpsnpBindTableResOverLoad(71), 
                l3aclFailed(72),
                fibArpFwdModeNumOverLoad(73),
                l2mcindex(74),
                ipmcindex(75),
                arpNumLack(76),
                ipv6NdNumLack(77),
                statNumLack(78),
                qosNumLack(79),
                l2vpnLinkLack(80),
                mcintNumLack(81),
                bfdaclNumLack(82),
                mcfibv4NumLack(83),
                mcfibv6NumLack(84),
                nhpNumLack(85),
                nscvmNumLack(86),
                mplsLinkLack(87),
                fibv4NumLack(88),
                fibv6NumLack(89),
                bgpExtNumLack(90),
                bgp6ExtNumLack(91),
                l2UserEntryOverload(92), 
                fwdGlobal1Token(93),
                fwdBoardToken(94),
                fwdGlobal2Token(95),
                fwdGlobal3Token(96),
                fwdGlobal4Token(97),
                fwdGlobal1ThresHoldToken(98),
                fwdBoardThresHoldToken(99), 
                fwdGlobal2ThresHoldToken(100),
                fwdGlobal3ThresHoldToken(101),
                fwdGlobal4ThresHoldToken(102),
                atIndex(103),
                flexQvctNum(104),
                inFlowWred(105),
                outFlowWred(106),
                inFlowMapping(107),
                outFlowMapping(108),
                inFlowQueueWfq(109),
                outFlowQueueWfq(110),
                inFlowQueueCbs(111),
                outFlowQueueCbs(112),
                inFlowQueuePbs(113),
                outFlowQueuePbs(114),
                inUserQueue(115),
                outUserQueue(116),
                inUserQueueTemp(117),
                outUserQueueTemp(118),
                inServiceTemp(119),
                outServiceTemp(120),
                inGQ(121),
                outGQ(122),
                inGQTemp(123),
                outGQTemp(124),
                inIfCar(125),
                outIfCar(126),
                inCarRemark(127),
                outCarRemark(128),
                gid(129),
                inAclCar(130),
                outAclCar(131),
                aclRe(132),
                aclNhp(133),
                inIPv4Acl(134),
                inIPv6Acl(135),
                outIPv4Acl(136),
                outIPv6Acl(137),
                inQppbCar(138),
                outQppbCar(139),
                inMirror(140),
                outMirror(141),
                inMirrorCapture(142),
                outMirrorCapture(143),
                inSuppressCar(144),
                outSuppressCar(145),
                inMirrorCar(146),
                outMirrorCar(147),
                aclNst(148),
                inProfSuppCar(149),
                outProfSuppCar(150),
                inProfSuppCarStat(151),
                outProfSuppCarStat(152),
                inProfSingleCar(153),
                outProfSingleCar(154),
                inProfSingleCarStat(155),
                outProfSingleCarStat(156),
                inAclStat(157),
                outAclStat(158),
                aclCarStat(159),
                inIfCarStat(160),
                outIfCarStat(161),
                inL2Acl(162),
                outL2Acl(163),
                inBehaviorSuppCar(191),
                outBehaviorSuppCar(192),
                qppbAcl(193),
                qppbGid(194) ,
                fwdInAc(168),
                fwdOutAc(169),
                fwdLem(170),
                fwdL2Entry(171),
                fwdMcMacfibv4(172),
                fwdSnoop(173),
                fwdArp(174)
                }
            MAX-ACCESS accessible-for-notify
            STATUS current
            DESCRIPTION
                "To describe the type of fowarding engine resource."
            ::= { hwFwdResTrapObject 3 }

        -- 1.3.6.1.4.1.2011.5.25.227.1.4
        hwFwdResThreshold OBJECT-TYPE
            SYNTAX Unsigned32
            MAX-ACCESS accessible-for-notify
            STATUS current
            DESCRIPTION
                "The threshold for trap."
            ::= { hwFwdResTrapObject 4 }

        -- 1.3.6.1.4.1.2011.5.25.227.1.5
        hwL3FailedService OBJECT-TYPE
            SYNTAX OCTET STRING(SIZE(0..128))
            MAX-ACCESS accessible-for-notify
            STATUS current
            DESCRIPTION
                "Layer 3 services failed to be delivered because of insufficient ACL resource."
            ::= { hwFwdResTrapObject 5 }  
            
        -- 1.3.6.1.4.1.2011.5.25.227.1.6
        hwCommand OBJECT-TYPE
            SYNTAX OCTET STRING(SIZE(0..256))
            MAX-ACCESS accessible-for-notify
            STATUS current
            DESCRIPTION
                "The Command failed to execute."
            ::= { hwFwdResTrapObject 6 }   
            
        -- 1.3.6.1.4.1.2011.5.25.227.1.7
        hwViewName OBJECT-TYPE
            SYNTAX OCTET STRING(SIZE(0..256))
            MAX-ACCESS accessible-for-notify
            STATUS current
            DESCRIPTION
                "The specific view of the command."
            ::= { hwFwdResTrapObject 7 }
        
        -- 1.3.6.1.4.1.2011.5.25.227.1.8
        hwReasonDescription OBJECT-TYPE
            SYNTAX OCTET STRING(SIZE(0..256))
            MAX-ACCESS accessible-for-notify
            STATUS current
            DESCRIPTION
                "The specific description for failed reason."
            ::= { hwFwdResTrapObject 8 }
        
		-- 1.3.6.1.4.1.2011.5.25.227.1.9
        hwFwdResLackVrId OBJECT-TYPE
            SYNTAX  Unsigned32
            MAX-ACCESS accessible-for-notify
            STATUS current
            DESCRIPTION
                "The current vrid."
            ::= { hwFwdResTrapObject 9 }
            
        -- 1.3.6.1.4.1.2011.5.25.227.2
        hwFwdResTraps OBJECT IDENTIFIER ::= { hwFwdResTrapMIB 2 }
        
        -- 1.3.6.1.4.1.2011.5.25.227.2.1
        hwFwdResLacTrap OBJECT IDENTIFIER ::= { hwFwdResTraps 1 }
        
        -- 1.3.6.1.4.1.2011.5.25.227.2.1.1
        hwWholeFwdResLack NOTIFICATION-TYPE
            OBJECTS { hwEntPhysicalindex, entPhysicalName, hwFwdResLackReasonId }
            STATUS current
            DESCRIPTION 
                "The whole device forwarding engine resources were overloaded."
            ::= { hwFwdResLacTrap 1 }
        
        -- 1.3.6.1.4.1.2011.5.25.227.2.1.2
        hwWholeFwdResLackResume NOTIFICATION-TYPE
            OBJECTS { hwEntPhysicalindex, entPhysicalName, hwFwdResLackReasonId }
            STATUS current
            DESCRIPTION 
                "The whole device forwarding engine resources were resumed."
            ::= { hwFwdResLacTrap 2 }
        
        -- 1.3.6.1.4.1.2011.5.25.227.2.1.3
        hwBoardFwdResLack NOTIFICATION-TYPE
            OBJECTS { hwEntPhysicalindex, entPhysicalName, hwFwdResLackSlotStr, hwFwdResLackReasonId }
            STATUS current
            DESCRIPTION 
                "The board forwarding engine resources were overloaded."
            ::= { hwFwdResLacTrap 3 }
        
        -- 1.3.6.1.4.1.2011.5.25.227.2.1.4
        hwBoardFwdResLackResume NOTIFICATION-TYPE
            OBJECTS { hwEntPhysicalindex, entPhysicalName, hwFwdResLackSlotStr, hwFwdResLackReasonId }
            STATUS current
            DESCRIPTION 
                "The board forwarding engine resources were resumed."
            ::= { hwFwdResLacTrap 4 }

        -- 1.3.6.1.4.1.2011.5.25.227.2.1.5
        hwBoardL3FwdResLack NOTIFICATION-TYPE
            OBJECTS { hwFwdResThreshold, hwEntPhysicalindex, entPhysicalName, hwFwdResLackSlotStr, hwFwdResLackReasonId }
            STATUS current
            DESCRIPTION 
                "The L3 forwarding engine resources were overloaded."
            ::= { hwFwdResLacTrap 5 }
        
        -- 1.3.6.1.4.1.2011.5.25.227.2.1.6
        hwBoardL3FwdResLackResume NOTIFICATION-TYPE
            OBJECTS { hwFwdResThreshold, hwEntPhysicalindex, entPhysicalName, hwFwdResLackSlotStr, hwFwdResLackReasonId }
            STATUS current
            DESCRIPTION 
                "The L3 forwarding engine resources were resumed."
            ::= { hwFwdResLacTrap 6 }
            
        -- 1.3.6.1.4.1.2011.5.25.227.2.1.7
        hwBoardL3ACLResLack NOTIFICATION-TYPE
            OBJECTS { hwL3FailedService, hwFwdResLackSlotStr, hwFwdResLackReasonId }
            STATUS current
            DESCRIPTION 
                "ACL failed to be delivered."
            ::= { hwFwdResLacTrap 7 }
            
        -- 1.3.6.1.4.1.2011.5.25.227.2.1.8
        hwBoardL2mcResLack NOTIFICATION-TYPE
            OBJECTS { hwFwdResThreshold, hwFwdResLackSlotStr, hwFwdResLackReasonId }
            STATUS current
            DESCRIPTION 
                "The l2mc index resources were overloaded."
            ::= { hwFwdResLacTrap 8 }    
                    
        -- 1.3.6.1.4.1.2011.5.25.227.2.1.9
        hwBoardL2mcResLackResume NOTIFICATION-TYPE
            OBJECTS { hwFwdResThreshold, hwFwdResLackSlotStr, hwFwdResLackReasonId }
            STATUS current
            DESCRIPTION 
                "The l2mc index resources were resumed."
            ::= { hwFwdResLacTrap 9 }        
            
        -- 1.3.6.1.4.1.2011.5.25.227.2.1.10
        hwBoardIpmcResLack NOTIFICATION-TYPE
            OBJECTS { hwFwdResThreshold, hwFwdResLackSlotStr, hwFwdResLackReasonId }
            STATUS current
            DESCRIPTION 
                "The ipmc index resources were overloaded."
            ::= { hwFwdResLacTrap 10 }       
                 
        -- 1.3.6.1.4.1.2011.5.25.227.2.1.11
        hwBoardIpmcResLackResume NOTIFICATION-TYPE
            OBJECTS { hwFwdResThreshold, hwFwdResLackSlotStr, hwFwdResLackReasonId }
            STATUS current
            DESCRIPTION 
                "The ipmc index resources were resumed."
            ::= { hwFwdResLacTrap 11 }          
            
        -- 1.3.6.1.4.1.2011.5.25.227.2.1.12
        hwBoardServiceFailed NOTIFICATION-TYPE
            OBJECTS { hwCommand, hwViewName, hwFwdResLackReasonId, hwReasonDescription, hwFwdResLackSlotStr }
            STATUS current
            DESCRIPTION 
                "Service failed because resources were overloaded."
            ::= { hwFwdResLacTrap 12 }

        -- 1.3.6.1.4.1.2011.5.25.227.2.1.13
        hwWholeFwdResThresholdExceed NOTIFICATION-TYPE
            OBJECTS { hwEntPhysicalindex, entPhysicalName, hwFwdResLackReasonId }
            STATUS current
            DESCRIPTION 
                        "The whole device forwarding engine resources exceeded the threshold."
            ::= { hwFwdResLacTrap 13 }
        
        -- 1.3.6.1.4.1.2011.5.25.227.2.1.14
        hwWholeFwdResThresholdExceedResume NOTIFICATION-TYPE
            OBJECTS { hwEntPhysicalindex, entPhysicalName, hwFwdResLackReasonId }
            STATUS current
            DESCRIPTION 
                        "The whole device forwarding engine resources fell from the threshold."
            ::= { hwFwdResLacTrap 14 }
        
        -- 1.3.6.1.4.1.2011.5.25.227.2.1.15
        hwBoardFwdResThresholdExceed NOTIFICATION-TYPE
            OBJECTS { hwEntPhysicalindex, entPhysicalName, hwFwdResLackSlotStr, hwFwdResLackReasonId }
            STATUS current
            DESCRIPTION 
                        "The board forwarding engine resources exceeded the threshold."
            ::= { hwFwdResLacTrap 15 }
        
        -- 1.3.6.1.4.1.2011.5.25.227.2.1.16
        hwBoardFwdResThresholdExceedResume NOTIFICATION-TYPE
            OBJECTS { hwEntPhysicalindex, entPhysicalName, hwFwdResLackSlotStr, hwFwdResLackReasonId }
            STATUS current
            DESCRIPTION 
                        "The board forwarding engine resources fell from the threshold."
            ::= { hwFwdResLacTrap 16 }

        -- 1.3.6.1.4.1.2011.5.25.227.2.1.17
        hwBoardMplsPhpNonsupport NOTIFICATION-TYPE
            OBJECTS { hwFwdResLackSlotStr}
            STATUS current
            DESCRIPTION 
                        "One or more boards do not support MPLS PHP."
            ::= { hwFwdResLacTrap 17 }
            
        -- 1.3.6.1.4.1.2011.5.25.227.2.1.18
        hwBoardResThresholdExceed NOTIFICATION-TYPE
            OBJECTS { hwFwdResLackSlotStr, hwFwdResThreshold, hwFwdResLackReasonId , hwReasonDescription}
            STATUS current
            DESCRIPTION 
                        "The board forwarding engine resources were overloaded."
            ::= { hwFwdResLacTrap 18 }
            
        -- 1.3.6.1.4.1.2011.5.25.227.2.1.19
        hwBoardResThresholdExceedResume NOTIFICATION-TYPE
            OBJECTS { hwFwdResLackSlotStr,hwFwdResThreshold, hwFwdResLackReasonId , hwReasonDescription }
            STATUS current
            DESCRIPTION 
                        "The board forwarding engine resources were resumed."
            ::= { hwFwdResLacTrap 19 }
			
	    -- 1.3.6.1.4.1.2011.5.25.227.2.1.20
        hwBoardResWarningThresholdExceed NOTIFICATION-TYPE
            OBJECTS {  hwFwdResLackSlotStr,hwFwdResThreshold,  hwFwdResLackReasonId , hwReasonDescription}
            STATUS current
            DESCRIPTION 
                        "The number of board forwarding engine resources reaches the threshold."
            ::= { hwFwdResLacTrap 20}
            
        -- 1.3.6.1.4.1.2011.5.25.227.2.1.21
        hwBoardResWarningThresholdExceedResume NOTIFICATION-TYPE
            OBJECTS { hwFwdResLackSlotStr,hwFwdResThreshold,  hwFwdResLackReasonId , hwReasonDescription}
            STATUS current
            DESCRIPTION 
                        "The number of board forwarding engine resources is less than the threshold."
            ::= { hwFwdResLacTrap 21 }
           
        -- 1.3.6.1.4.1.2011.5.25.227.2.1.22
        hwBoardIPv6ACLResLack NOTIFICATION-TYPE
            OBJECTS { hwViewName,hwFwdResLackSlotStr}
            STATUS current
            DESCRIPTION 
                        "Service failed because of insufficient resources."
            ::= { hwFwdResLacTrap 22 }

        -- 1.3.6.1.4.1.2011.5.25.227.3
        hwFwdResTrapConformance OBJECT IDENTIFIER ::= { hwFwdResTrapMIB 3 }
        
        -- 1.3.6.1.4.1.2011.5.25.227.3.1
        hwFwdResTrapCompliances OBJECT IDENTIFIER ::= { hwFwdResTrapConformance 1 }
        
        -- 1.3.6.1.4.1.2011.5.25.227.3.1.1
        hwFwdResTrapCompliance MODULE-COMPLIANCE
            STATUS current
            DESCRIPTION 
                "Compliance statement for agents that provide full support for hwBaseTrapMIB."
            MODULE -- this module
                MANDATORY-GROUPS { hwFwdResObjectGroup }
            ::= { hwFwdResTrapCompliances 1 }
        
        -- 1.3.6.1.4.1.2011.5.25.227.3.2
        hwFwdResTrapGroups OBJECT IDENTIFIER ::= { hwFwdResTrapConformance 2 }
        
        -- 1.3.6.1.4.1.2011.5.25.227.3.2.1
        hwFwdResObjectGroup OBJECT-GROUP
            OBJECTS { hwEntPhysicalindex, hwFwdResLackSlotStr, hwFwdResLackReasonId, hwFwdResThreshold, hwL3FailedService, hwCommand, hwViewName, hwReasonDescription,hwFwdResLackVrId }
            STATUS current
            DESCRIPTION 
                "Group for base trap objects."
            ::= { hwFwdResTrapGroups 1 }
        
        -- 1.3.6.1.4.1.2011.5.25.227.3.2.2
        hwFwdResTrapGroup NOTIFICATION-GROUP
            NOTIFICATIONS { hwWholeFwdResLack, hwWholeFwdResLackResume, hwBoardFwdResLack, hwBoardFwdResLackResume, hwBoardL3FwdResLack, hwBoardL3FwdResLackResume, hwBoardL3ACLResLack,
            hwBoardL2mcResLack, hwBoardL2mcResLackResume, hwBoardIpmcResLack, hwBoardIpmcResLackResume, hwBoardServiceFailed, hwWholeFwdResThresholdExceed, 
            hwWholeFwdResThresholdExceedResume, hwBoardFwdResThresholdExceed, hwBoardFwdResThresholdExceedResume,hwBoardMplsPhpNonsupport,
            hwBoardResThresholdExceed,hwBoardResThresholdExceedResume,hwBoardResWarningThresholdExceed,hwBoardResWarningThresholdExceedResume,hwBoardIPv6ACLResLack 
            }
            STATUS current
            DESCRIPTION 
                "Group for all base traps."
            ::= { hwFwdResTrapGroups 2 }
        
    
    END

--
-- HUAWEI-FWD-RES-TRAP-MIB.mib
--
