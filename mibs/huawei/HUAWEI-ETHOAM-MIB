-- =================================================================
-- Copyright (C) 2010 by  HUAWEI TECHNOLOGIES. All rights reserved.
--
-- Description: HUAWEI-ETHOAM-MIB
-- Reference:
-- Version:     V2.17
-- History:
-- Revision history
--            REVISION     "201405060000Z"        
--            DESCRIPTION  "V2.17, Modify the description of hwY1731LckExceedThreshold, hwY1731LckExceedThresholdRecovery"
--            REVISION     "201404260000Z"        
--            DESCRIPTION  "V2.16, Add hwY1731LckExceedThreshold, hwY1731LckExceedThresholdRecovery"
--            REVISION     "201404090000Z"        
--            DESCRIPTION  "V2.15, Add hwY1731SingleLossStatistic8021pValue, hwY1731OneDelayStatistic8021pValue, hwY1731TwoDelayStatistic8021pValue"
--            REVISION     "201312040000Z"        
--            DESCRIPTION  "V1.10, Add hwCfmVlanOneDelayTrapLogDelayValueHigh, hwCfmVlanOneDelayTrapLogDelayValueLow, hwCfmVlanOneDelayRecoveryTrapLogDelayValueHigh, 
--                      hwCfmVlanOneDelayRecoveryTrapLogDelayValueLow, hwCfmVlanTwoDelayTrapLogDelayValueHigh, hwCfmVlanTwoDelayTrapLogDelayValueLow,
--                      hwY1731StatisticTrapLogValueHigh, hwY1731StatisticTrapLogValueLow, hwCfmVlanTwoDelayRecoveryTrapLogDelayValueHigh, hwCfmVlanTwoDelayRecoveryTrapLogDelayValueLow"
--            REVISION     "201310070000Z"        
--            DESCRIPTION  "V1.09, Add hwY1731TestIdTable,hwY1731TestIdSingleEndedLMSendTable,hwY1731TestIdSingleEndedLMReceiveTable,
--                      hwY1731TestIdOneWayDMSendTable,hwY1731TestIdOneWayDMSendTable,hwY1731TestIdTwoWayDMSendTable,hwY1731TestIdTwoWayDMReceiveTable,
--                      hwY1731TestIdSingleLossStatTable,hwY1731TestIdOneDelayStatTable,hwY1731TestIdTwoDelayStatTable,hwY1731TestIdStatisticResetTable,hwY1731MaxTestId for multiflow mib"
--            REVISION     "201304011045Z"        
--            DESCRIPTION  "V1.08, hwY1731ServiceType add unbind value"
--            REVISION     "201207030000Z"        
--            DESCRIPTION  "V1.07, add hwY1731OneDelayPacketSize, hwY1731TwoDelayPacketSize"
--            REVISION     "2012050240000Z"        
--            DESCRIPTION  "V1.07, add hwY1731LckDefect, hwY1731LckDefectCleared"
--            REVISION     "201202080000Z"        
--            DESCRIPTION  "V1.07, add hwY1731TwoDelayUnresponsivePacketCount leaf node for HK-GAN y1731 statistics"
--            REVISION     "201201300000Z"        
--            DESCRIPTION  "V1.06, add hwDot3ahEfmInterval leaf node for efm interval configuration"  
--            REVISION     "201109090000Z"        
--            DESCRIPTION  "V1.05, add hwY1731AisExceedMaxPktNumCleared leaf node for AIS"
--            REVISION     "201109090000Z"        
--            DESCRIPTION  "V1.05, add hwY1731AisMaxPktNum leaf node for AIS"
--            REVISION     "201109090000Z"        
--            DESCRIPTION  "V1.05, add hwY1731AisExceedMaxPktNum leaf node for AIS"
--            REVISION     "201109050000Z"        
--            DESCRIPTION  "V1.05, add hwY1731SingleLossLocalMax, hwY1731SingleLossLocalMin, hwY1731SingleLossLocalAvg, 
--                      hwY1731SingleLossRemoteMax, hwY1731SingleLossRemoteMin, hwY1731SingleLossRemoteAvg,
--                      hwY1731OneDelayStatisticMax, hwY1731OneDelayStatisticMin, hwY1731OneDelayStatisticAvg, 
--                      hwY1731TwoDelayStatisticMax, hwY1731TwoDelayStatisticMin, hwY1731TwoDelayStatisticAvg"
--            REVISION     "201105230000Z"        
--            DESCRIPTION  "V1.05, add hwDot1agCfmMdFormatName, hwDot1agCfmMaFormat, hwDot1agCfmMaFormatName for new 1ag MD/MA format support"      
--            REVISION     "201105110000Z"        
--            DESCRIPTION  "V1.05, add  hwDot1agCfmUnexpectedMEGLevel, 
--                          hwDot1agCfmUnexpectedMEGLevelCleared, hwDot1agCfmMismerge, hwDot1agCfmMismergeCleared, 
--                          hwDot1agCfmUnexpectedMEP, hwDot1agCfmUnexpectedMEPCleared, hwDot1agCfmUnexpectedPeriod, 
--                          hwDot1agCfmUnexpectedPeriodCleared, hwDot1agCfmUnexpectedMAC, hwDot1agCfmUnexpectedMACCleared, 
--                          hwDot1agCfmLOC, hwDot1agCfmLOCCleared, hwDot1agCfmExceptionalMACStatusfor new 1ag traps support"
--            REVISION     "201104210000Z"        
--            DESCRIPTION  "V1.05, add hwY1731AisVlanConfigTable table for ais vlan configuration"
--            REVISION     "201103230000Z"
--            DESCRIPTION  "V1.05, add hwDot3ahEfmLoopbackFailed, hwY1731AisDefectAlarm, hwY1731AisDefectAlarmRecovery trap node for PTN6900"
--            REVISION     "201102130000Z"        
--            DESCRIPTION  "V1.04, add hwDot3ahEfmHoldUpTime leaf node for efm holdup timer configuration"
--            REVISION     "201012040000Z"        
--            DESCRIPTION  "V1.03, add hwY1731ResetStatistic8021pValue leaf nodes for Y1731 COS 
--                          statistic configuration"
--            REVISION     "201011120000Z"        
--            DESCRIPTION  "V1.02, add hwY1731SingleLossRecv8021pValue and hwY1731OneDelayRecv8021pValue,hwY1731TwoDelayRecv8021pValue 
--                         leaf nodes for Y1731 COS statistic configuration"
--            REVISION     "201011010000Z"        
--            DESCRIPTION  "V1.01, add hwDot3ahEfmTimeout leaf node for efm timeout configuration"
-- ==================================================================

    HUAWEI-ETHOAM-MIB DEFINITIONS ::= BEGIN

        IMPORTS
            CounterBasedGauge64
                FROM HCNUM-TC
            hwDatacomm
                FROM HUAWEI-MIB
            ifIndex, InterfaceIndex, InterfaceIndexOrZero, ifDescr
                FROM IF-MIB
            EnabledStatus
                FROM P-BRIDGE-MIB
            VlanIdOrNone
                FROM Q-BRIDGE-MIB
            OBJECT-GROUP, MODULE-COMPLIANCE, NOTIFICATION-GROUP
                FROM SNMPv2-CONF
            Integer32, Unsigned32, Counter32, BITS, OBJECT-TYPE, IpAddress,Counter64,
            MODULE-IDENTITY, NOTIFICATION-TYPE
                FROM SNMPv2-SMI
            MacAddress, TruthValue, RowStatus, TimeInterval, TimeStamp,
            TEXTUAL-CONVENTION
                FROM SNMPv2-TC;


        hwEthOamMib MODULE-IDENTITY
            LAST-UPDATED "201405060000Z"        
            ORGANIZATION
                "Huawei Technologies Co.,Ltd."
            CONTACT-INFO
                "Huawei Industrial Base
                  Bantian, Longgang
                   Shenzhen 518129
                   People's Republic of China
                   Website: http://www.huawei.com
                   Email: support@huawei.com
                 "
            DESCRIPTION
                "Ethernet OAM MIB"
		 REVISION     "201405060000Z"
		 DESCRIPTION  "V2.17, Modify the description of hwY1731LckExceedThreshold, hwY1731LckExceedThresholdRecovery"
		 REVISION     "201404260000Z"
		 DESCRIPTION  "V2.16, Add hwY1731LckExceedThreshold, hwY1731LckExceedThresholdRecovery"
                 REVISION     "201404090000Z"  
                 DESCRIPTION  "support on-demand OAM config 802.1p. Add hwY1731SingleLossStatistic8021pValue, 
                                                hwY1731OneDelayStatistic8021pValue, hwY1731TwoDelayStatistic8021pValue"
                 REVISION     "201312040000Z"  
                 DESCRIPTION  "extended  DM statistical data to 64bit, added the following nodes:
                                                hwCfmVlanOneDelayTrapLogDelayValueHigh, hwCfmVlanOneDelayTrapLogDelayValueLow, 
                                                hwCfmVlanOneDelayRecoveryTrapLogDelayValueHigh, hwCfmVlanOneDelayRecoveryTrapLogDelayValueLow, 
                                                hwCfmVlanTwoDelayTrapLogDelayValueHigh, hwCfmVlanTwoDelayTrapLogDelayValueLow,
                                                hwY1731StatisticTrapLogValueHigh, hwY1731StatisticTrapLogValueLow, 
                                                hwCfmVlanTwoDelayRecoveryTrapLogDelayValueHigh, hwCfmVlanTwoDelayRecoveryTrapLogDelayValueLow"
                 REVISION     "201310070000Z"  
                 DESCRIPTION  "modified for multiflow mib"
                 REVISION     "201304011045Z"
                 DESCRIPTION  "modified by 00145247"
                 REVISION     "201302061102Z"
                 DESCRIPTION  "modified by 00218832"

            ::= { hwEthOam 1 }




--
-- Textual conventions
--

        HWDetectType ::= TEXTUAL-CONVENTION
            STATUS current
            DESCRIPTION
                "
                Detect the mode type:
                Fast detect and standard detect
                "
            SYNTAX INTEGER
                {
                normalDetect(1),
                fastDetect(2)
                }

--  Textual conventions for OAM MIB
--
        HWDot3Oui ::= TEXTUAL-CONVENTION
            STATUS current
            DESCRIPTION
                "24-bit Organizationally Unique Identifier.  Information on
                OUIs can be found in IEEE 802-2001 [802-2001] Clause 9."
            SYNTAX OCTET STRING (SIZE (3))

        HWTestMessageSendSpeed ::= TEXTUAL-CONVENTION
            STATUS current
            DESCRIPTION
                "
                Transmission rate:
                1Mbps and 5Mbps.
                "
            SYNTAX INTEGER
                {
                oneMbps(1),
                fiveMbps(2)
                }

        HWTestMessageFinishedValue ::= TEXTUAL-CONVENTION
            STATUS current
            DESCRIPTION
                "
                The five values indicates: has not run/is running/the previous test terminates normally/the previous test terminates abnormally/the previous test is interrupted (through ctrl+c or mib)
                "
            REFERENCE
                "                  "
            SYNTAX INTEGER
                {
                ready(1),
                testing(2),
                finished(3),
                failed(4),
                stop(5)
                }

--  RFC2863
        HWDot1agCfmRelayActionFieldValue ::= TEXTUAL-CONVENTION
            STATUS current
            DESCRIPTION
                "Indicates the possible values the Relay action field can take."
            REFERENCE
                "802.1ag clauses 12.14.7.5.3 g), 20.32.2.5, and Table 21-24"
            SYNTAX INTEGER
                {
                rlyHit(1),
                rlyFdb(2),
                rlyMpdb(3),
                rlyInvalid(255)
                }

        HWDot1agCfmIngressActionFieldValue ::= TEXTUAL-CONVENTION
            STATUS current
            DESCRIPTION
                "Possible values returned in the ingress action field."
            REFERENCE
                "802.1ag clauses 12.14.7.5.3 k), 21.9.9.1, 20.35.2.6 and
                Table 21-26.
                 "
            SYNTAX INTEGER
                {
                ingOk(1),
                ingDown(2),
                ingBlocked(3),
                ingVid(4),
                ingInvalid(255)
                }

        HWDot1agCfmEgressActionFieldValue ::= TEXTUAL-CONVENTION
            STATUS current
            DESCRIPTION
                "Possible values returned in the egress action field"
            REFERENCE
                "802.1ag clauses 12.14.7.5.3 o), 21.9.10.1 and Table 21-28"
            SYNTAX INTEGER
                {
                egrOK(1),
                egrDown(2),
                egrBlocked(3),
                egrVid(4),
                egrInvalid(255)
                }

        HWDot1agCfmHighestDefectPri ::= TEXTUAL-CONVENTION
            STATUS current
            DESCRIPTION
                "An enumerated value, equal to the contents of the variable
                highestDefect (20.33.9 and Table 20-1), indicating the
                highest-priority defect that has been present since the MEP
                Fault Notification Generator State Machine was last in the
                FNG_RESET state, either:

                none(0)           no defects since FNG_RESET
                defRDICCM(1)      DefRDICCM
                defMACstatus(2)   DefMACstatus
                defRemoteCCM(3)   DefRemoteCCM
                defErrorCCM(4)    DefErrorCCM
                defXconCCM(5)     DefXconCCM

                The value 0 is used for no defects so that additional higher
                priority values can be added, if needed, at a later time, and
                so that these values correspond with those in
                Dot1agCfmLowestAlarmPri.
                "
            REFERENCE
                "20.1.2, 12.14.7.7.2:c and 20.33.9"
            SYNTAX INTEGER
                {
                none              (0),
                defRDICCM         (1),
                defMACstatus      (2),
                defRemoteCCM      (3),
                defErrorCCM       (4),
                defXconCCM        (5)
                }

        HWDot1agCfmMDLevel ::= TEXTUAL-CONVENTION
            DISPLAY-HINT "d"
            STATUS current
            DESCRIPTION
                "Integer identifying the Maintenance Domain Level (MD Level).
                Higher numbers correspond to higher Maintenance Domains,
                those with the greatest physical reach, with the highest
                values for customers' CFM PDUs.  Lower numbers correspond
                to lower Maintenance Domains, those with more limited
                physical reach, with the lowest values for CFM PDUs
                protecting single bridges or physical links.
                "
            REFERENCE
                "802.1ag clauses 18.3, 21.4.1"
            SYNTAX Integer32 (0..7)


--
-- Node definitions
--

        hwEthOam OBJECT IDENTIFIER ::= { hwDatacomm 136 }


        hwEthOam1ag OBJECT IDENTIFIER ::= { hwEthOamMib 1 }


        hwDot1agCfmEnabled OBJECT-TYPE
            SYNTAX EnabledStatus
            MAX-ACCESS read-write
            STATUS current
            DESCRIPTION
                "
                This object indicates whether CFM is enabled globally.
                The value of this object can be:
                  Enabled: indicates that CFM is enabled globally.
                  Disabled: indicates that global CFM is disabled
                "
            ::= { hwEthOam1ag 1 }


        hwDot1agCfmVersion OBJECT-TYPE
            SYNTAX INTEGER
                {
                draft7(1),
                standard(2)
                }
            MAX-ACCESS read-write
            STATUS current
            DESCRIPTION
                "
                This object indicates the supported CFM version.
                The value of this object can be:
                  draft: indicates IEEE 802.1ag Draft 7.
                  standard: indicates IEEE Standard 802.1ag-2007.
                "
            ::= { hwEthOam1ag 2 }


        hwDot1agCfmMdObject OBJECT IDENTIFIER ::= { hwEthOam1ag 3 }


        hwDot1agCfmMdTableNextIndex OBJECT-TYPE
            SYNTAX Unsigned32
            MAX-ACCESS read-only
            STATUS current
            DESCRIPTION
                "
                The index to the Maintenance Domain table.

                hwDot1agCfmMdTableNextIndex needs to be inspected to find an
                available index for row-creation.
                "
            ::= { hwDot1agCfmMdObject 1 }


        hwDot1agCfmMdTable OBJECT-TYPE
            SYNTAX SEQUENCE OF HwDot1agCfmMdEntry
            MAX-ACCESS not-accessible
            STATUS current
            DESCRIPTION
                "
                This table is used to create a Maintenance Domain (MD).

                A Maintenance Domain is described in 802.1ag (3.22) as the
                network or the part of the network for which faults in
                connectivity are to be managed. The boundary of a Maintenance
                Domain is defined by a set of DSAPs, each of which can become
                a point of connectivity to a service instance.
                "
            REFERENCE
                "802.1ag clause 3.16 and 18.2"
            ::= { hwDot1agCfmMdObject 2 }


        hwDot1agCfmMdEntry OBJECT-TYPE
            SYNTAX HwDot1agCfmMdEntry
            MAX-ACCESS not-accessible
            STATUS current
            DESCRIPTION
                "
                The Maintenance Domain table entry. This entry is not lost
                upon reboot. It is backed up by stable storage.
                "
            INDEX { hwDot1agCfmMdIndex }
            ::= { hwDot1agCfmMdTable 1 }


        HwDot1agCfmMdEntry ::=
            SEQUENCE {
                hwDot1agCfmMdIndex
                    Unsigned32,
                hwDot1agCfmMdFormat
                    INTEGER,
                hwDot1agCfmMdName
                    OCTET STRING,
                hwDot1agCfmMdMdLevel
                    HWDot1agCfmMDLevel,
                hwDot1agCfmMdMhfCreation
                    INTEGER,
                hwDot1agCfmMdMhfIdPermission
                    INTEGER,
                hwDot1agCfmMdFormatName
                    OCTET STRING,
                hwDot1agCfmMdRowStatus
                    RowStatus
             }

        hwDot1agCfmMdIndex OBJECT-TYPE
            SYNTAX Unsigned32
            MAX-ACCESS not-accessible
            STATUS current
            DESCRIPTION
                "
                This object indicates the index of the MD Table.

                hwDot1agCfmMdTableNextIndex needs to be inspected to find an
                available index for row-creation.
                "
            ::= { hwDot1agCfmMdEntry 1 }


        hwDot1agCfmMdFormat OBJECT-TYPE
            SYNTAX INTEGER
                {
                noMdName(1),
                dns(2),
                macAddress(3),
                string(4)
                }
            MAX-ACCESS read-create
            STATUS current
            DESCRIPTION
                "
                This object indicates the format of the MD name.
                By default, the value is string.
                "
            DEFVAL { string }
            ::= { hwDot1agCfmMdEntry 2 }


        hwDot1agCfmMdName OBJECT-TYPE
            SYNTAX OCTET STRING (SIZE (1..43))
            MAX-ACCESS read-create
            STATUS current
            DESCRIPTION
                "
                This object indicates the name of the MD.
                The type/format of this object is determined by the value
                of the hwDot1agCfmMdFormat object.

                Each Maintenance Domain has unique name amongst all those
                used or available to a service provider or operator.  It
                facilitates easy identification of administrative
                responsibility for each Maintenance Domain.
                "
            ::= { hwDot1agCfmMdEntry 3 }


        hwDot1agCfmMdMdLevel OBJECT-TYPE
            SYNTAX HWDot1agCfmMDLevel
            MAX-ACCESS read-create
            STATUS current
            DESCRIPTION
                "
                This object indicates the level of the MD.
                The value ranges from 0 to 7. The greater the value, the higher the preference.
                By default, the value is 0.
                "
            DEFVAL { 0 }
            ::= { hwDot1agCfmMdEntry 4 }


        hwDot1agCfmMdMhfCreation OBJECT-TYPE
            SYNTAX INTEGER
                {
                defMHFnone(1),
                defMHFdefault(2),
                defMHFexplicit(3)
                }
            MAX-ACCESS read-create
            STATUS current
            DESCRIPTION
                "
                This object indicates whether the management entity can create MIPs for the MD.
                The value of this object can be:
                  defMHFnone: indicates that the MIPs are not automatically created.
                  defMHFdefault: indicates that the management entity automatically
                                 creates MIPs based on certain rules.
                  defMHFexplicit: indicates that the management entity automatically
                                  creates MIPs based on certain rules.
                By default, the value is defMHFnone.
                "
            DEFVAL { defMHFnone }
            ::= { hwDot1agCfmMdEntry 5 }


        hwDot1agCfmMdMhfIdPermission OBJECT-TYPE
            SYNTAX INTEGER
                {
                sendIdNone(1),
                sendIdChassis(2),
                sendIdManage(3),
                sendIdChassisManage(4),
                sendIdDefer(5)
                }
            MAX-ACCESS read-create
            STATUS current
            DESCRIPTION
                "
                This object indicates what is to be included in the Sender ID TLV
                transmitted by MPs configured in the MD. The value of this object
                can be:
                  sendIdNone: indicates that the Sender ID TLV is not to be sent.
                  sendIdChassis: indicates that the Sender ID TLV to be sent contains
                                 the chassis ID information.
                  sendIdManage: indicates that the Sender ID TLV to be sent contains
                                management address information.
                  sendIdChassisManage: indicates that the Sender ID TLV to be sent
                                       contains both chassis ID information and
                                       management address information.
                  sendIdDefer: indicates that the contents of the Sender ID TLV to be
                               sent are determined by the MD management entity.
                By default, the value is sendIdDefer.
                "
            DEFVAL { sendIdDefer }
            ::= { hwDot1agCfmMdEntry 6 }
            
        
        hwDot1agCfmMdFormatName OBJECT-TYPE
            SYNTAX OCTET STRING (SIZE (0..43))
            MAX-ACCESS read-create
            STATUS current
            DESCRIPTION
                "
                This object indicates the MD format name.
                The type/format of this object is determined by the value
                of the hwDot1agCfmMdFormatName object.

                Each Maintenance Domain has unique name amongst all those
                used or available to a service provider or operator.  It
                facilitates easy identification of administrative
                responsibility for each Maintenance Domain.
                "
            ::= { hwDot1agCfmMdEntry 7 }


        hwDot1agCfmMdRowStatus OBJECT-TYPE
            SYNTAX RowStatus
            MAX-ACCESS read-create
            STATUS current
            DESCRIPTION
                "
                This object indicates the row status of this table.

                The writable columns in a row can not be changed if the row
                is active. All columns MUST have a valid value before a row
                can be activated.
                "
            ::= { hwDot1agCfmMdEntry 99 }


        hwDot1agCfmMaObject OBJECT IDENTIFIER ::= { hwEthOam1ag 4 }


        hwDot1agCfmMaNextIndex OBJECT-TYPE
            SYNTAX Unsigned32
            MAX-ACCESS read-only
            STATUS current
            DESCRIPTION
                "
                Value to be used as the index of the MA table entries.
                "
            ::= { hwDot1agCfmMaObject 1 }


        hwDot1agCfmMaTable OBJECT-TYPE
            SYNTAX SEQUENCE OF HwDot1agCfmMaEntry
            MAX-ACCESS not-accessible
            STATUS current
            DESCRIPTION
                "
                This table is used to create a Maintenance Association (MA).
                Each row in the table represents an MA.
                An MA is a set of MEPs, each configured with a single service instance.
                "
            REFERENCE
                "802.1ag clause 3.16 and 18.2"
            ::= { hwDot1agCfmMaObject 2 }


        hwDot1agCfmMaEntry OBJECT-TYPE
            SYNTAX HwDot1agCfmMaEntry
            MAX-ACCESS not-accessible
            STATUS current
            DESCRIPTION
                "The MA table entry."
            INDEX { hwDot1agCfmMdIndex, hwDot1agCfmMaIndex }
            ::= { hwDot1agCfmMaTable 1 }


        HwDot1agCfmMaEntry ::=
            SEQUENCE {
                hwDot1agCfmMaIndex
                    Unsigned32,
                hwDot1agCfmMaName
                    OCTET STRING,
                hwDot1agCfmMaMapType
                    INTEGER,
                hwDot1agCfmMaMapVlanValue
                    VlanIdOrNone,
                hwDot1agCfmMaMapVsiName
                    OCTET STRING,
                hwDot1agCfmMaMapL2vcValue
                    Unsigned32,
                hwDot1agCfmMaMapL2vcType
                    INTEGER,
                hwDot1agCfmMaPktPriority
                    Integer32,
                hwDot1agCfmMaCcmInterval
                    INTEGER,
                hwDot1agCfmMaRmepActiveTime
                    Integer32,
                hwDot1agCfmMaMepFngAlarmTime
                    Integer32,
                hwDot1agCfmMaMepFngResetTime
                    Integer32,
                hwDot1agCfmMaFormat
                    INTEGER,
                hwDot1agCfmMaFormatName
                    OCTET STRING,
                hwDot1agCfmMaRowStatus
                    RowStatus
             }

        hwDot1agCfmMaIndex OBJECT-TYPE
            SYNTAX Unsigned32
            MAX-ACCESS not-accessible
            STATUS current
            DESCRIPTION
                "
                This object indicates the index of the MA table.
                "
            ::= { hwDot1agCfmMaEntry 1 }


        hwDot1agCfmMaName OBJECT-TYPE
            SYNTAX OCTET STRING (SIZE (1..43))
            MAX-ACCESS read-create
            STATUS current
            DESCRIPTION
                "
                This object indicates the name of the MA.
                This name MUST be unique within a maintenance domain.
                "
            ::= { hwDot1agCfmMaEntry 2 }


        hwDot1agCfmMaMapType OBJECT-TYPE
            SYNTAX INTEGER
                {
                mapVlan(1),
                mapVsi(2),
                mapL2vc(3),
                unbind(4)
                }
            MAX-ACCESS read-create
            STATUS current
            DESCRIPTION
                "
                This object indicates what is associated with the MA.
                The value of this object can be:
                  mapVlan: indicates that a VLAN is associated with the current MA.
                  mapVsi: indicates that a VSI is associated with the current MA.
                  mapL2vc: indicates that an L2VC is associated with the current MA.
                  unbind: indicates that the MA is not associated with any VLAN, VSI or L2VC.
                By default, the value is unbind.
                "
            DEFVAL { unbind }
            ::= { hwDot1agCfmMaEntry 3 }

        hwDot1agCfmMaMapVlanValue OBJECT-TYPE
            SYNTAX VlanIdOrNone
            MAX-ACCESS read-create
            STATUS current
            DESCRIPTION
                "This object indicates the ID of the VLAN associated with the MA."
            ::= { hwDot1agCfmMaEntry 4 }

        hwDot1agCfmMaMapVsiName OBJECT-TYPE
            SYNTAX OCTET STRING (SIZE (1..31))
            MAX-ACCESS read-create
            STATUS current
            DESCRIPTION
                "This object indicates the name of the VSI associated with the MA."
            ::= { hwDot1agCfmMaEntry 5 }

        hwDot1agCfmMaMapL2vcValue OBJECT-TYPE
            SYNTAX Unsigned32
            MAX-ACCESS read-create
            STATUS current
            DESCRIPTION
                "
                This object indicates the ID of the L2VC associated with the MA.
                "
            ::= { hwDot1agCfmMaEntry 6 }

        hwDot1agCfmMaMapL2vcType OBJECT-TYPE
            SYNTAX INTEGER
                {
                invalid(1),
                l2vcRaw(2),
                l2vcTagged(3)
                }
            MAX-ACCESS read-create
            STATUS current
            DESCRIPTION
                "
                This object indicates the encapsulation type of the L2VC associated with the MA.
                The value of this object can be:
                  invalid: indicates that no display shows that the L2VC is associated
                           with the current MA.
                  l2vcRaw: indicates that the VLAN tag is not encapsulated into the packet.
                  l2vcTagged: indicates that the VLAN tag is encapsulated into the packet.
                By default, the value is invalid.
                "
            DEFVAL { invalid }
            ::= { hwDot1agCfmMaEntry 7 }

        hwDot1agCfmMaPktPriority OBJECT-TYPE
            SYNTAX Integer32 (0..7)
            MAX-ACCESS read-create
            STATUS current
            DESCRIPTION
                "
                This object indicates the priority of the 802.1ag packet sent in the MA.
                The value ranges from 0 to 7. The greater the value is, the higher the priority is.
                By default, the value is 7.
                "
            REFERENCE
                "802.1ag clause 12.14.6.1.4"
            DEFVAL { 7 }
            ::= { hwDot1agCfmMaEntry 8 }

        hwDot1agCfmMaCcmInterval OBJECT-TYPE
            SYNTAX INTEGER
                {
                interval10ms(1),
                interval20ms(2),
                interval30ms(3),
                interval50ms(4),
                interval100ms(5),
                interval1s(6),
                interval10s(7),
                interval3Dot3ms(8),
                interval1min(9),
                interval10min(10)
                }
            MAX-ACCESS read-create
            STATUS current
            DESCRIPTION
                "
                This object indicates the interval for an MEP in the MA to send
                or probe CCMs. The value of this object can be:
                  3.3 milliseconds
                  10 milliseconds
                  20 milliseconds
                  30 milliseconds
                  50 milliseconds
                  100 milliseconds
                  1 second
                  10 seconds
                  1 minute
                  10 minutes
                By default, the value is 1 second.
                "
            REFERENCE
                "802.1ag clause 12.14.6.1.3"
            DEFVAL { interval1s }
            ::= { hwDot1agCfmMaEntry 9 }

        hwDot1agCfmMaRmepActiveTime OBJECT-TYPE
            SYNTAX Integer32 (0..600)
            MAX-ACCESS read-create
            STATUS current
            DESCRIPTION
                "
                This object indicates the time period after which RMEP configurations
                are to be activated. The value ranges from 0 to 600 in seconds.
                By default, the value is 0.
                "
            DEFVAL { 0 }
            ::= { hwDot1agCfmMaEntry 10 }

        hwDot1agCfmMaMepFngAlarmTime OBJECT-TYPE
            SYNTAX Integer32 (0..30000)
            MAX-ACCESS read-create
            STATUS current
            DESCRIPTION
                "
                This object indicates the delay for the RMEP to send trap messages.
                The value must be an integer multiple of 500, for example, 500, 1000,
                or 1500.
                The value ranges from 0 to 30000 in milliseconds.
                By default, the value is 2500.
                "
            DEFVAL { 2500 }
            ::= { hwDot1agCfmMaEntry 11 }

        hwDot1agCfmMaMepFngResetTime OBJECT-TYPE
            SYNTAX Integer32 (0..30000)
            MAX-ACCESS read-create
            STATUS current
            DESCRIPTION
                "
                This object indicates the delay for the RMEP to send alarm clearance
                messages after the fault is rectified.
                The value must be an integer multiple of 500, for example, 500, 1000,
                or 1500.
                The value ranges from 0 to 30000 in milliseconds.
                By default, the value is 10000.
                "
            DEFVAL { 10000 }
            ::= { hwDot1agCfmMaEntry 12 }

        hwDot1agCfmMaFormat OBJECT-TYPE
            SYNTAX INTEGER
                {
                string(2),
                iccBased(32)
                }
            MAX-ACCESS read-create
            STATUS current
            DESCRIPTION
                "
                This object indicates the format of the MA name.
                string: indicates that the format of the MA name is string.
                icc-based: indicates that the format of the MA name is ICC-based.
                By default, the value is string.
                "
            DEFVAL { string }
            ::= { hwDot1agCfmMaEntry 13 }
            
        hwDot1agCfmMaFormatName OBJECT-TYPE
            SYNTAX OCTET STRING (SIZE (1..43))
            MAX-ACCESS read-create
            STATUS current
            DESCRIPTION
                "
                This object indicates the MA format name.
                The type/format of this object is determined by the value
                of the hwDot1agCfmMaFormatName object.
                "
            ::= { hwDot1agCfmMaEntry 14 }


        hwDot1agCfmMaRowStatus OBJECT-TYPE
            SYNTAX RowStatus
            MAX-ACCESS read-create
            STATUS current
            DESCRIPTION
                "
                This object indicates the row status of this table.

                The writable columns in a row can not be changed if the row
                is active. All columns MUST have a valid value before a row
                can be activated.
                "
            ::= { hwDot1agCfmMaEntry 99 }

        hwDot1agCfmMepObject OBJECT IDENTIFIER ::= { hwEthOam1ag 5 }


        hwDot1agCfmMepTable OBJECT-TYPE
            SYNTAX SEQUENCE OF HwDot1agCfmMepEntry
            MAX-ACCESS not-accessible
            STATUS current
            DESCRIPTION
                "
                This table is used to create a Maintenance Association End Point (MEP).
                "
            REFERENCE
                "802.1ag clauses 3.17, 12.14.7 and 19.2"
            ::= { hwDot1agCfmMepObject 1 }


        hwDot1agCfmMepEntry OBJECT-TYPE
            SYNTAX HwDot1agCfmMepEntry
            MAX-ACCESS not-accessible
            STATUS current
            DESCRIPTION
                "
                The MEP table entry.
                "
            INDEX { hwDot1agCfmMdIndex, hwDot1agCfmMaIndex, hwDot1agCfmMepIdentifier }
            ::= { hwDot1agCfmMepTable 1 }


        HwDot1agCfmMepEntry ::=
            SEQUENCE {
                hwDot1agCfmMepIdentifier
                    Integer32,
                hwDot1agCfmMepIsVlanType
                    TruthValue,
                hwDot1agCfmMepIfIndex
                    InterfaceIndexOrZero,
                hwDot1agCfmMepDot1qVlan
                    VlanIdOrNone,
                hwDot1agCfmMepPeVlan
                    VlanIdOrNone,
                hwDot1agCfmMepCeVlan
                    VlanIdOrNone,
                hwDot1agCfmMepDirection
                    INTEGER,
                hwDot1agCfmMepCcmSendEnabled
                    EnabledStatus,
                hwDot1agCfmMepMacAddress
                    MacAddress,
                hwDot1agCfmMepRowStatus
                    RowStatus
             }

        hwDot1agCfmMepIdentifier OBJECT-TYPE
            SYNTAX Integer32 (1..8191)
            MAX-ACCESS accessible-for-notify
            STATUS current
            DESCRIPTION
                "
                This object indicates the ID of the MEP.
                Integer that is unique among all the MEPs in the same MA.
                MEP Identifier is also known as the MEPID.
                The value ranges from 1 to 8191.
                "
            ::= { hwDot1agCfmMepEntry 1 }


        hwDot1agCfmMepIsVlanType OBJECT-TYPE
            SYNTAX TruthValue
            MAX-ACCESS read-create
            STATUS current
            DESCRIPTION
                "
                This object indicates whether the MEP in the MA is a VLAN-based MEP.
                If the MEP is a VLAN-based MEP, the MA must have been associated
                with a VLAN and the interface and VLAN information need not be configured.
                If the MEP is not a VLAN-based MEP, entry creation fails.
                "
            ::= { hwDot1agCfmMepEntry 2 }


        hwDot1agCfmMepIfIndex OBJECT-TYPE
            SYNTAX InterfaceIndexOrZero
            MAX-ACCESS read-create
            STATUS current
            DESCRIPTION
                "
                This object indicates the interface to which the MEP is bound.
                The interface is either a bridge port, or an aggregated IEEE 802.1
                link within a bridge port, to which the MEP is attached.
                By default, the value of IfIndex is 0.
                "
            DEFVAL { 0 }
            ::= { hwDot1agCfmMepEntry 3 }


        hwDot1agCfmMepDot1qVlan OBJECT-TYPE
            SYNTAX VlanIdOrNone
            MAX-ACCESS read-create
            STATUS current
            DESCRIPTION
                "
                This object indicates the VLAN to which the interface that the MEP
                is bound to belong.
                "
            ::= { hwDot1agCfmMepEntry 4 }


        hwDot1agCfmMepPeVlan OBJECT-TYPE
            SYNTAX VlanIdOrNone
            MAX-ACCESS read-create
            STATUS current
            DESCRIPTION
                "
                This object indicates the QinQ PE VLAN bound to the MEP.
                "
            ::= { hwDot1agCfmMepEntry 5 }


        hwDot1agCfmMepCeVlan OBJECT-TYPE
            SYNTAX VlanIdOrNone
            MAX-ACCESS read-create
            STATUS current
            DESCRIPTION
                "
                This object indicates the QinQ CE VLAN bound to the MEP.
                "
            ::= { hwDot1agCfmMepEntry 6 }


        hwDot1agCfmMepDirection OBJECT-TYPE
            SYNTAX INTEGER
                {
                invalid(1),
                dirInward(2),
                dirOutward(3)
                }
            MAX-ACCESS read-create
            STATUS current
            DESCRIPTION
                "
                This object indicates the direction in which the MEP sends the 802.1ag
                protocol packets.
                The value of this object can be:
                  invalid: indicates the invalid value.
                  dirInward: indicates that the 802.1ag protocol packets sent by an
                             inward-facing MEP are transmitted through all the interfaces
                             in the VLAN associated with the current MA (except the
                             interface where the MEP resides). That is, an inward-facing
                             MEP broadcasts the 802.1ag protocol packets in the VLAN
                             associated with the current MA.
                  dirOutward: indicates that the 802.1ag protocol packets sent by an
                              outward-facing MEP are transmitted directly through the
                              interface on which the MEP resides.
                By default, the value is invalid.
                "
            DEFVAL { invalid }
            ::= { hwDot1agCfmMepEntry 7 }


        hwDot1agCfmMepCcmSendEnabled OBJECT-TYPE
            SYNTAX EnabledStatus
            MAX-ACCESS read-create
            STATUS current
            DESCRIPTION
                "
                This object indicates whether CCM sending is enabled on the MEP in an MA.
                The value of this object can be:
                  enabled
                  disabled
                By default, the value is disabled.
                "
            REFERENCE
                "802.1ag clauses 12.14.7.1.3 and 20.9.1"
            DEFVAL { disabled }
            ::= { hwDot1agCfmMepEntry 8 }


        hwDot1agCfmMepMacAddress OBJECT-TYPE
            SYNTAX MacAddress
            MAX-ACCESS read-only
            STATUS current
            DESCRIPTION
                "
                This object indicates the MAC address of an MEP.
                "
            ::= { hwDot1agCfmMepEntry 9 }


        hwDot1agCfmMepRowStatus OBJECT-TYPE
            SYNTAX RowStatus
            MAX-ACCESS read-create
            STATUS current
            DESCRIPTION
                "
                This object indicates the row status of this table.

                The writable columns in a row can not be changed if the row
                is active. All columns MUST have a valid value before a row
                can be activated.
                "
            ::= { hwDot1agCfmMepEntry 99 }


        hwDot1agCfmRMepObject OBJECT IDENTIFIER ::= { hwEthOam1ag 6 }


        hwDot1agCfmRMepTable OBJECT-TYPE
            SYNTAX SEQUENCE OF HwDot1agCfmRMepEntry
            MAX-ACCESS not-accessible
            STATUS current
            DESCRIPTION
                "
                This table is used to create a Remote Maintenance Association End Point (RMEP).
                "
            ::= { hwDot1agCfmRMepObject 1 }


        hwDot1agCfmRMepEntry OBJECT-TYPE
            SYNTAX HwDot1agCfmRMepEntry
            MAX-ACCESS not-accessible
            STATUS current
            DESCRIPTION
                "
                The remote MEP table entity.
                "
            INDEX { hwDot1agCfmMdIndex, hwDot1agCfmMaIndex, hwDot1agCfmRMepIdentifier }
            ::= { hwDot1agCfmRMepTable 1 }


        HwDot1agCfmRMepEntry ::=
            SEQUENCE {
                hwDot1agCfmRMepIdentifier
                    Integer32,
                hwDot1agCfmRMepMacAddress
                    MacAddress,
                hwDot1agCfmRMepCcmRecvEnabled
                    EnabledStatus,
                hwDot1agCfmRMepStateIsUp
                    INTEGER,
                hwDot1agCfmRMepHighestPrDefect
                    HWDot1agCfmHighestDefectPri,
                hwDot1agCfmRMepRowStatus
                    RowStatus
             }

        hwDot1agCfmRMepIdentifier OBJECT-TYPE
            SYNTAX Integer32 (1..8191)
            MAX-ACCESS accessible-for-notify
            STATUS current
            DESCRIPTION
                "
                This object indicates the ID of the RMEP.
                The value ranges from 1 to 8191.
                "
            ::= { hwDot1agCfmRMepEntry 1 }


        hwDot1agCfmRMepMacAddress OBJECT-TYPE
            SYNTAX MacAddress
            MAX-ACCESS read-create
            STATUS current
            DESCRIPTION
                "
                This object indicates the MAC address of the interface
                the RMEP resides.
                "
            ::= { hwDot1agCfmRMepEntry 2 }


        hwDot1agCfmRMepCcmRecvEnabled OBJECT-TYPE
            SYNTAX EnabledStatus
            MAX-ACCESS read-create
            STATUS current
            DESCRIPTION
                "
                This object indicates whether CCM receiving is enabled on the current device.
                The value can be:
                  enabled
                  disabled
                By default, the value is disabled.
                "
            DEFVAL { disabled }
            ::= { hwDot1agCfmRMepEntry 3 }


        hwDot1agCfmRMepStateIsUp OBJECT-TYPE
            SYNTAX INTEGER
                {
                    up(1),
                    down(2),
                    invalid(3)
                }
            MAX-ACCESS read-only
            STATUS current
            DESCRIPTION
                "
                This object indicates the CFM status. The value can be:
                  up: indicates that the CFM status is Up.
                  down: indicates that the CFM status is Down.
                  invalid: indicates that the CFM status is not enabled.
                "
            ::= { hwDot1agCfmRMepEntry 4 }


        hwDot1agCfmRMepHighestPrDefect OBJECT-TYPE
            SYNTAX HWDot1agCfmHighestDefectPri
            MAX-ACCESS read-only
            STATUS current
            DESCRIPTION
                "
                This object indicates the severity level of the fault on an RMEP.
                If the CFM status is Up, this object is displayed as none.
                "
            REFERENCE
                "802.1ag clause 12.14.7.1.3  20.32.9 and Table 20-1"
            ::= { hwDot1agCfmRMepEntry 5 }


        hwDot1agCfmRMepRowStatus OBJECT-TYPE
            SYNTAX RowStatus
            MAX-ACCESS read-create
            STATUS current
            DESCRIPTION
                "
                This object indicates the row status of this table.

                The writable columns in a row can not be changed if the row
                is active. All columns MUST have a valid value before a row
                can be activated.
                "
            ::= { hwDot1agCfmRMepEntry 99 }


        hwDot1agCfmMipObject OBJECT IDENTIFIER ::= { hwEthOam1ag 7 }


        hwDot1agCfmMipTable OBJECT-TYPE
            SYNTAX SEQUENCE OF HwDot1agCfmMipEntry
            MAX-ACCESS not-accessible
            STATUS current
            DESCRIPTION
                "
                This table is used to display information about a Maintenance
                Association Intermediate Point (MIP).
                "
            ::= { hwDot1agCfmMipObject 1 }


        hwDot1agCfmMipEntry OBJECT-TYPE
            SYNTAX HwDot1agCfmMipEntry
            MAX-ACCESS not-accessible
            STATUS current
            DESCRIPTION
                "
                The MIP table entry.
                "
            INDEX { hwDot1agCfmMipIfIndex }
            ::= { hwDot1agCfmMipTable 1 }


        HwDot1agCfmMipEntry ::=
            SEQUENCE {
                hwDot1agCfmMipIfIndex
                    InterfaceIndex,
                hwDot1agCfmMipLevel
                    HWDot1agCfmMDLevel,
                hwDot1agCfmMipIfMacAddress
                    MacAddress
             }

        hwDot1agCfmMipIfIndex OBJECT-TYPE
            SYNTAX InterfaceIndex
            MAX-ACCESS not-accessible
            STATUS current
            DESCRIPTION
                "
                This object indicates the interface on which the MIP resides.
                "
            ::= { hwDot1agCfmMipEntry 1 }


        hwDot1agCfmMipLevel OBJECT-TYPE
            SYNTAX HWDot1agCfmMDLevel
            MAX-ACCESS read-only
            STATUS current
            DESCRIPTION
                "
                This object indicates the level of the MIP.
                The value ranges from 0 to 7.
                "
            REFERENCE
                "802.1ag clause 12.14.5.1.3 b)"
            ::= { hwDot1agCfmMipEntry 2 }


        hwDot1agCfmMipIfMacAddress OBJECT-TYPE
            SYNTAX MacAddress
            MAX-ACCESS read-only
            STATUS current
            DESCRIPTION
                "
                This object indicates the MAC address of the interface on which the MIP resides.
                "
            ::= { hwDot1agCfmMipEntry 3 }


        hwDot1agCfmMacPingObject OBJECT IDENTIFIER ::= { hwEthOam1ag 8 }


        hwDot1agCfmMacPingTable OBJECT-TYPE
            SYNTAX SEQUENCE OF HwDot1agCfmMacPingEntry
            MAX-ACCESS not-accessible
            STATUS current
            DESCRIPTION
                "
                The entries related to the Mac Ping include the parameters input
                by users and the returned results.
                "
            ::= { hwDot1agCfmMacPingObject 1 }


        hwDot1agCfmMacPingEntry OBJECT-TYPE
            SYNTAX HwDot1agCfmMacPingEntry
            MAX-ACCESS not-accessible
            STATUS current
            DESCRIPTION
                "
                This table is used to configure the MAC ping function.
                "
            INDEX { hwDot1agCfmMacPingIndex }
            ::= { hwDot1agCfmMacPingTable 1 }


        HwDot1agCfmMacPingEntry ::=
            SEQUENCE {
                hwDot1agCfmMacPingIndex
                    Unsigned32,
                hwDot1agCfmMacPingState
                    EnabledStatus,
                hwDot1agCfmMacPingMdName
                    OCTET STRING,
                hwDot1agCfmMacPingMaName
                    OCTET STRING,
                hwDot1agCfmMacPingMepId
                    Integer32,
                hwDot1agCfmMacPingDestIsMepId
                    TruthValue,
                hwDot1agCfmMacPingDestMepId
                    Integer32,
                hwDot1agCfmMacPingMacAddress
                    MacAddress,
                hwDot1agCfmMacPingOutIfIndex
                    InterfaceIndexOrZero,
                hwDot1agCfmMacPingTimeOut
                    Unsigned32,
                hwDot1agCfmMacPingCount
                    Unsigned32,
                hwDot1agCfmMacPingPacketSize
                    Integer32,
                hwDot1agCfmMacPingPriority
                    Integer32,
                hwDot1agCfmMacPingSendPacketNum
                    Counter32,
                hwDot1agCfmMacPingRecvPacketNum
                    Counter32,
                hwDot1agCfmMacPingPacketLossRatio
                    Unsigned32,
                hwDot1agCfmMacPingRecvTimeDelayMin
                    Unsigned32,
                hwDot1agCfmMacPingRecvTimeDelayMax
                    Unsigned32,
                hwDot1agCfmMacPingRecvTimeDelayAvg
                    Unsigned32,
                hwDot1agCfmMacPingRowStatus
                    RowStatus
             }


        hwDot1agCfmMacPingIndex OBJECT-TYPE
            SYNTAX Unsigned32
            MAX-ACCESS not-accessible
            STATUS current
            DESCRIPTION
                "
                This object indicates the index of this table.
                "
            ::= { hwDot1agCfmMacPingEntry 1 }


        hwDot1agCfmMacPingState OBJECT-TYPE
            SYNTAX EnabledStatus
            MAX-ACCESS read-create
            STATUS current
            DESCRIPTION
                "
                This object indicates whether the MAC ping function is enabled.
                The value can be:
                  enabled
                  disabled
                By default, the value is disabled.
                "
            DEFVAL { disabled }
            ::= { hwDot1agCfmMacPingEntry 2 }


        hwDot1agCfmMacPingMdName OBJECT-TYPE
            SYNTAX OCTET STRING (SIZE (1..43))
            MAX-ACCESS read-create
            STATUS current
            DESCRIPTION
                "
                This object indicates the name of the MD where MAC ping is performed.
                "
            ::= { hwDot1agCfmMacPingEntry 3 }


        hwDot1agCfmMacPingMaName OBJECT-TYPE
            SYNTAX OCTET STRING (SIZE (1..43))
            MAX-ACCESS read-create
            STATUS current
            DESCRIPTION
                "
                This object indicates the name of the MA where MAC ping is performed.
                "
            ::= { hwDot1agCfmMacPingEntry 4 }


        hwDot1agCfmMacPingMepId OBJECT-TYPE
            SYNTAX Integer32 (0 | 1..8191)
            MAX-ACCESS read-create
            STATUS current
            DESCRIPTION
                "
                This object indicates the ID of the local MEP of the 802.1ag MAC ping operation.
                The value ranges from 1 to 8191.
                By default, the value is 0.
                "
            DEFVAL { 0 }
            ::= { hwDot1agCfmMacPingEntry 5 }


        hwDot1agCfmMacPingDestIsMepId OBJECT-TYPE
            SYNTAX TruthValue
            MAX-ACCESS read-create
            STATUS current
            DESCRIPTION
                "
                This object indicates whether the destination MAC address of the LBM
                is the MAC address of the interface on which the RMEP resides.
                "
            ::= { hwDot1agCfmMacPingEntry 6 }


        hwDot1agCfmMacPingDestMepId OBJECT-TYPE
            SYNTAX Integer32 (0 | 1..8191)
            MAX-ACCESS read-create
            STATUS current
            DESCRIPTION
                "
                This object indicates the ID of the destination RMEP of the 802.1ag
                MAC ping operation.
                The value ranges from 1 to 8191.
                By default, the value is 0.
                "
            DEFVAL { 0 }
            ::= { hwDot1agCfmMacPingEntry 7 }


        hwDot1agCfmMacPingMacAddress OBJECT-TYPE
            SYNTAX MacAddress
            MAX-ACCESS read-create
            STATUS current
            DESCRIPTION
                "
                This object indicates the destination MAC address of the LBM.
                "
            ::= { hwDot1agCfmMacPingEntry 8 }


        hwDot1agCfmMacPingOutIfIndex OBJECT-TYPE
            SYNTAX InterfaceIndexOrZero
            MAX-ACCESS read-create
            STATUS current
            DESCRIPTION
                "
                This object indicates the outbound interface that sends the LBM.
                "
            DEFVAL { 0 }
            ::= { hwDot1agCfmMacPingEntry 9 }


        hwDot1agCfmMacPingTimeOut OBJECT-TYPE
            SYNTAX Unsigned32 (1..65535)
            MAX-ACCESS read-create
            STATUS current
            DESCRIPTION
                "
                This object indicates the timeout period for waiting for the LBR.
                The value ranges from 1 to 65535 in milliseconds.
                By default, the value is 2000.
                "
            DEFVAL { 2000 }
            ::= { hwDot1agCfmMacPingEntry 10 }


        hwDot1agCfmMacPingCount OBJECT-TYPE
            SYNTAX Unsigned32 (1..4294967295)
            MAX-ACCESS read-create
            STATUS current
            DESCRIPTION
                "
                This object indicates the number of ping operation times.
                The value ranges from 1 to 4294967295.
                By default, the value is 5.
                "
            DEFVAL { 5 }
            ::= { hwDot1agCfmMacPingEntry 11 }


        hwDot1agCfmMacPingPacketSize OBJECT-TYPE
            SYNTAX Integer32 (64..2000)
            MAX-ACCESS read-create
            STATUS current
            DESCRIPTION
                "
                This object indicates the length of the LBM.
                The value ranges from 64 to 2000.
                By default, the value is 95.
                "
            DEFVAL { 95 }
            ::= { hwDot1agCfmMacPingEntry 12 }


        hwDot1agCfmMacPingPriority OBJECT-TYPE
            SYNTAX Integer32 (0..7 | 255 )
            MAX-ACCESS read-create
            STATUS current
            DESCRIPTION
                "
                This object indicates the priority of the sent LBM packet.
                The value ranges from 0 to 7 or can be 255. The value 255 is an invalid value.
                If the value is set to 255, this value should be identical with the priority value of the MA which the MEP belongs to.
                The greater the value is, the higher the priority is.
                "
            DEFVAL { 255 }
            ::= { hwDot1agCfmMacPingEntry 13 }


        hwDot1agCfmMacPingSendPacketNum OBJECT-TYPE
            SYNTAX Counter32
            MAX-ACCESS read-only
            STATUS current
            DESCRIPTION
                "
                This object indicates the number of sent LBMs.
                "
            ::= { hwDot1agCfmMacPingEntry 14 }


        hwDot1agCfmMacPingRecvPacketNum OBJECT-TYPE
            SYNTAX Counter32
            MAX-ACCESS read-only
            STATUS current
            DESCRIPTION
                "
                This object indicates the number of received LBRs.
                "
            ::= { hwDot1agCfmMacPingEntry 15 }


        hwDot1agCfmMacPingPacketLossRatio OBJECT-TYPE
            SYNTAX Unsigned32 (0..100)
            MAX-ACCESS read-only
            STATUS current
            DESCRIPTION
                "
                This object indicates the frame loss ratio on the physical link.
                The value ranges from 0 to 100.
                "
            ::= { hwDot1agCfmMacPingEntry 16 }


        hwDot1agCfmMacPingRecvTimeDelayMin OBJECT-TYPE
            SYNTAX Unsigned32
            MAX-ACCESS read-only
            STATUS current
            DESCRIPTION
                "
                This object indicates the minimum delay in receiving the LBM.
                "
            ::= { hwDot1agCfmMacPingEntry 17 }


        hwDot1agCfmMacPingRecvTimeDelayMax OBJECT-TYPE
            SYNTAX Unsigned32
            MAX-ACCESS read-only
            STATUS current
            DESCRIPTION
                "
                This object indicates the maximum delay in receiving the LBM.
                "
            ::= { hwDot1agCfmMacPingEntry 18 }


        hwDot1agCfmMacPingRecvTimeDelayAvg OBJECT-TYPE
            SYNTAX Unsigned32
            MAX-ACCESS read-only
            STATUS current
            DESCRIPTION
                "
                This object indicates the average delay in receiving the LBM.
                "
            ::= { hwDot1agCfmMacPingEntry 19 }


        hwDot1agCfmMacPingRowStatus OBJECT-TYPE
            SYNTAX RowStatus
            MAX-ACCESS read-create
            STATUS current
            DESCRIPTION
                "
                This object indicates the row status of this table.

                The writable columns in a row can not be changed if the row
                is active. All columns MUST have a valid value before a row
                can be activated.
                "
            ::= { hwDot1agCfmMacPingEntry 99 }


        hwDot1agCfmMacTraceObjects OBJECT IDENTIFIER ::= { hwEthOam1ag 9 }


        hwDot1agCfmMacTraceTable OBJECT-TYPE
            SYNTAX SEQUENCE OF HwDot1agCfmMacTraceEntry
            MAX-ACCESS not-accessible
            STATUS current
            DESCRIPTION
                "
                This table is used to configure the MAC trace function.
                "
            ::= { hwDot1agCfmMacTraceObjects 1 }


        hwDot1agCfmMacTraceEntry OBJECT-TYPE
            SYNTAX HwDot1agCfmMacTraceEntry
            MAX-ACCESS not-accessible
            STATUS current
            DESCRIPTION
                "
                Indicates the MAC Trace table entry.
                "
            INDEX { hwDot1agCfmMacTraceIndex }
            ::= { hwDot1agCfmMacTraceTable 1 }


        HwDot1agCfmMacTraceEntry ::=
            SEQUENCE {
                hwDot1agCfmMacTraceIndex
                    Unsigned32,
                hwDot1agCfmMacTraceState
                    EnabledStatus,
                hwDot1agCfmMacTraceMdName
                    OCTET STRING,
                hwDot1agCfmMacTraceMaName
                    OCTET STRING,
                hwDot1agCfmMacTraceMepId
                    Integer32,
                hwDot1agCfmMacTraceDestIsMepId
                    TruthValue,
                hwDot1agCfmMacTraceDestMepId
                    Integer32,
                hwDot1agCfmMacTraceMacAddress
                    MacAddress,
                hwDot1agCfmMacTraceOutIfIndex
                    InterfaceIndexOrZero,
                hwDot1agCfmMacTraceTimeOut
                    Unsigned32,
                hwDot1agCfmMacTraceTTL
                    Unsigned32,
                hwDot1agCfmMacTraceSendSeqNumber
                    Unsigned32,
                hwDot1agCfmMacTraceResult
                    INTEGER,
                hwDot1agCfmMacTraceRowStatus
                    RowStatus
             }


        hwDot1agCfmMacTraceIndex OBJECT-TYPE
            SYNTAX Unsigned32
            MAX-ACCESS not-accessible
            STATUS current
            DESCRIPTION
                "
                This object indicates the index of this table.
                "
            ::= { hwDot1agCfmMacTraceEntry 1 }


        hwDot1agCfmMacTraceState OBJECT-TYPE
            SYNTAX EnabledStatus
            MAX-ACCESS read-create
            STATUS current
            DESCRIPTION
                "
                This object indicates whether the MAC trace function is enabled.
                The value can be:
                  enabled
                  disabled
                By default, the value is disabled.
                "
            DEFVAL { disabled }
            ::= { hwDot1agCfmMacTraceEntry 2 }


        hwDot1agCfmMacTraceMdName OBJECT-TYPE
            SYNTAX OCTET STRING (SIZE (1..43))
            MAX-ACCESS read-create
            STATUS current
            DESCRIPTION
                "
                This object indicates the name of the MD where MAC trace is performed.
                "
            ::= { hwDot1agCfmMacTraceEntry 3 }

        hwDot1agCfmMacTraceMaName OBJECT-TYPE
            SYNTAX OCTET STRING (SIZE (1..43))
            MAX-ACCESS read-create
            STATUS current
            DESCRIPTION
                "
                This object indicates the name of the MA where MAC trace is performed.
                "
            ::= { hwDot1agCfmMacTraceEntry 4 }


        hwDot1agCfmMacTraceMepId OBJECT-TYPE
            SYNTAX Integer32 (0 | 1..8191)
            MAX-ACCESS read-create
            STATUS current
            DESCRIPTION
                "
                This object indicates the ID of the local MEP of the 802.1ag
                MAC trace operation.
                The value ranges from 1 to 8191.
                By default, the value is 0.
                "
            DEFVAL { 0 }
            ::= { hwDot1agCfmMacTraceEntry 5 }


        hwDot1agCfmMacTraceDestIsMepId OBJECT-TYPE
            SYNTAX TruthValue
            MAX-ACCESS read-create
            STATUS current
            DESCRIPTION
                "
                This object indicates whether the destination MAC address of the LTM
                is the MAC address of the interface on which the RMEP resides.
                "
            ::= { hwDot1agCfmMacTraceEntry 6 }


        hwDot1agCfmMacTraceDestMepId OBJECT-TYPE
            SYNTAX Integer32 (0 | 1..8191)
            MAX-ACCESS read-create
            STATUS current
            DESCRIPTION
                "
                This object indicates the ID of the destination RMEP of the 802.1ag
                MAC trace operation.
                The value ranges from 1 to 8191.
                By default, the value is 0.
                "
            DEFVAL { 0 }
            ::= { hwDot1agCfmMacTraceEntry 7 }


        hwDot1agCfmMacTraceMacAddress OBJECT-TYPE
            SYNTAX MacAddress
            MAX-ACCESS read-create
            STATUS current
            DESCRIPTION
                "
                This object indicates the destination MAC address of the LTM.
                "
            ::= { hwDot1agCfmMacTraceEntry 8 }


        hwDot1agCfmMacTraceOutIfIndex OBJECT-TYPE
            SYNTAX InterfaceIndexOrZero
            MAX-ACCESS read-create
            STATUS current
            DESCRIPTION
                "
                This object indicates the outbound interface that sends the LTM.
                "
            DEFVAL { 0 }
            ::= { hwDot1agCfmMacTraceEntry 9 }


        hwDot1agCfmMacTraceTimeOut OBJECT-TYPE
            SYNTAX Unsigned32 (1..65535)
            MAX-ACCESS read-create
            STATUS current
            DESCRIPTION
                "
                This object indicates the timeout period for waiting for the LTR.
                The value ranges from 1 to 65535, in milliseconds.
                By default, the value is 2000.
                "
            DEFVAL { 2000 }
            ::= { hwDot1agCfmMacTraceEntry 10 }


        hwDot1agCfmMacTraceTTL OBJECT-TYPE
            SYNTAX Unsigned32 (1..255)
            MAX-ACCESS read-create
            STATUS current
            DESCRIPTION
                "
                This object indicates the TTL value of the 802.1ag MAC trace operation.
                The value ranges from 1 to 255.
                By default, the value is 64.
                "
            DEFVAL { 64 }
            ::= { hwDot1agCfmMacTraceEntry 11 }


        hwDot1agCfmMacTraceSendSeqNumber OBJECT-TYPE
            SYNTAX Unsigned32
            MAX-ACCESS read-only
            STATUS current
            DESCRIPTION
                "
                This object indicates the sequence number of the sent LTR.
                "
            ::= { hwDot1agCfmMacTraceEntry 12 }


        hwDot1agCfmMacTraceResult OBJECT-TYPE
            SYNTAX INTEGER
                {
                invalid(1),
                successful(2),
                failed(3)
                }
            MAX-ACCESS read-only
            STATUS current
            DESCRIPTION
                "
                This object indicates the result of the MAC trace operation.
                "
            ::= { hwDot1agCfmMacTraceEntry 13 }


        hwDot1agCfmMacTraceRowStatus OBJECT-TYPE
            SYNTAX RowStatus
            MAX-ACCESS read-create
            STATUS current
            DESCRIPTION
                "
                This object indicates the row status of this table.

                The writable columns in a row can not be changed if the row
                is active. All columns MUST have a valid value before a row
                can be activated.
                "
            ::= { hwDot1agCfmMacTraceEntry 99 }


        hwDot1agCfmMacTraceReplyTable OBJECT-TYPE
            SYNTAX SEQUENCE OF HwDot1agCfmMacTraceReplyEntry
            MAX-ACCESS not-accessible
            STATUS current
            DESCRIPTION
                "
                This table is used to display information about the LTR for responding
                to the MAC trace operation.
                "
            ::= { hwDot1agCfmMacTraceObjects 2 }


        hwDot1agCfmMacTraceReplyEntry OBJECT-TYPE
            SYNTAX HwDot1agCfmMacTraceReplyEntry
            MAX-ACCESS not-accessible
            STATUS current
            DESCRIPTION
                "
                The Mac Trace result table entry.
                "
            INDEX { hwDot1agCfmMacTraceReplySeqNumber, hwDot1agCfmMacTraceReplyRecvOrder }
            ::= { hwDot1agCfmMacTraceReplyTable 1 }


        HwDot1agCfmMacTraceReplyEntry ::=
            SEQUENCE {
                hwDot1agCfmMacTraceReplySeqNumber
                    Unsigned32,
                hwDot1agCfmMacTraceReplyRecvOrder
                    Unsigned32,
                hwDot1agCfmMacTraceReplyTTL
                    Unsigned32,
                hwDot1agCfmMacTraceReplyForwarded
                    TruthValue,
                hwDot1agCfmMacTraceReplyTerminalMep
                    TruthValue,
                hwDot1agCfmMacTraceReplyRelayAction
                    HWDot1agCfmRelayActionFieldValue,
                hwDot1agCfmMacTraceReplyIngressAction
                    HWDot1agCfmIngressActionFieldValue,
                hwDot1agCfmMacTraceReplyIngressMac
                    MacAddress,
                hwDot1agCfmMacTraceReplyIngressIfName
                    OCTET STRING,
                hwDot1agCfmMacTraceReplyEgressAction
                    HWDot1agCfmEgressActionFieldValue,
                hwDot1agCfmMacTraceReplyEgressMac
                    MacAddress,
                hwDot1agCfmMacTraceReplyEgressIfName
                    OCTET STRING
             }

        hwDot1agCfmMacTraceReplySeqNumber OBJECT-TYPE
            SYNTAX Unsigned32
            MAX-ACCESS not-accessible
            STATUS current
            DESCRIPTION
                "
                This object indicates the index of this table.
                The value is the sequence number of the LTR.
                "
            REFERENCE
                "802.1ag clause 12.14.7.5"
            ::= { hwDot1agCfmMacTraceReplyEntry 1 }


        hwDot1agCfmMacTraceReplyRecvOrder OBJECT-TYPE
            SYNTAX Unsigned32
            MAX-ACCESS not-accessible
            STATUS current
            DESCRIPTION
                "
                This object indicates the index of this table.
                The value is the sequence in which the MAC trace results are displayed.
                "
            ::= { hwDot1agCfmMacTraceReplyEntry 2 }


        hwDot1agCfmMacTraceReplyTTL OBJECT-TYPE
            SYNTAX Unsigned32 (0..255)
            MAX-ACCESS read-only
            STATUS current
            DESCRIPTION
                "
                This object indicates the TTL of the LTR.
                The value ranges from 0 to 255.
                "
            ::= { hwDot1agCfmMacTraceReplyEntry 3 }


        hwDot1agCfmMacTraceReplyForwarded OBJECT-TYPE
            SYNTAX TruthValue
            MAX-ACCESS read-only
            STATUS current
            DESCRIPTION
                "
                This object indicates whether the device that sends the LTR keeps on
                forwarding LTMs.
                "
            ::= { hwDot1agCfmMacTraceReplyEntry 4 }


        hwDot1agCfmMacTraceReplyTerminalMep OBJECT-TYPE
            SYNTAX TruthValue
            MAX-ACCESS read-only
            STATUS current
            DESCRIPTION
                "
                This object indicates whether the LTR is sent by an MEP.
                "
            ::= { hwDot1agCfmMacTraceReplyEntry 5 }


        hwDot1agCfmMacTraceReplyRelayAction OBJECT-TYPE
            SYNTAX HWDot1agCfmRelayActionFieldValue
            MAX-ACCESS read-only
            STATUS current
            DESCRIPTION
                "
                This object indicates the value of the Relay Action field in the LTR.
                "
            ::= { hwDot1agCfmMacTraceReplyEntry 6 }



        hwDot1agCfmMacTraceReplyIngressAction OBJECT-TYPE
            SYNTAX HWDot1agCfmIngressActionFieldValue
            MAX-ACCESS read-only
            STATUS current
            DESCRIPTION
                "
                This object indicates the value of the Ingress Action field in the LTR.
                "
            ::= { hwDot1agCfmMacTraceReplyEntry 7 }


        hwDot1agCfmMacTraceReplyIngressMac OBJECT-TYPE
            SYNTAX MacAddress
            MAX-ACCESS read-only
            STATUS current
            DESCRIPTION
                "
                This object indicates the physical MAC address carried in the ingress
                MAC address field in the LTR.
                "
            ::= { hwDot1agCfmMacTraceReplyEntry 8 }


        hwDot1agCfmMacTraceReplyIngressIfName OBJECT-TYPE
            SYNTAX OCTET STRING
            MAX-ACCESS read-only
            STATUS current
            DESCRIPTION
                "
                This object indicates the name of the inbound interface of the LTR.
                "
            ::= { hwDot1agCfmMacTraceReplyEntry 9 }


        hwDot1agCfmMacTraceReplyEgressAction OBJECT-TYPE
            SYNTAX HWDot1agCfmEgressActionFieldValue
            MAX-ACCESS read-only
            STATUS current
            DESCRIPTION
                "
                This object indicates the value of the Egress Action field in the LTR.
                "
            ::= { hwDot1agCfmMacTraceReplyEntry 10 }


        hwDot1agCfmMacTraceReplyEgressMac OBJECT-TYPE
            SYNTAX MacAddress
            MAX-ACCESS read-only
            STATUS current
            DESCRIPTION
                "
                This object indicates the physical MAC address carried in the egress
                MAC address field in the LTR.
                "
            ::= { hwDot1agCfmMacTraceReplyEntry 11 }


        hwDot1agCfmMacTraceReplyEgressIfName OBJECT-TYPE
            SYNTAX OCTET STRING
            MAX-ACCESS read-only
            STATUS current
            DESCRIPTION
                "
                This object indicates the name of the interface that forwards the LTR.
                "
            ::= { hwDot1agCfmMacTraceReplyEntry 12 }



        hwDot1agCfmQueryObject OBJECT IDENTIFIER ::= { hwEthOam1ag 10 }


        hwDot1agCfmQueryMdIndexTable OBJECT-TYPE
            SYNTAX SEQUENCE OF HwDot1agCfmQueryMdIndexEntry
            MAX-ACCESS not-accessible
            STATUS current
            DESCRIPTION
                "
                This table is used to get the index of the Maintenance Domain table.
                "
            ::= { hwDot1agCfmQueryObject 1 }


        hwDot1agCfmQueryMdIndexEntry OBJECT-TYPE
            SYNTAX HwDot1agCfmQueryMdIndexEntry
            MAX-ACCESS not-accessible
            STATUS current
            DESCRIPTION
                "
                The Md Index table entry.
                "
            INDEX { hwDot1agCfmQueryMdName }
            ::= { hwDot1agCfmQueryMdIndexTable 1 }


        HwDot1agCfmQueryMdIndexEntry ::=
            SEQUENCE {
                hwDot1agCfmQueryMdName
                    OCTET STRING,
                hwDot1agCfmQueryMdIndex
                    Unsigned32
             }


        hwDot1agCfmQueryMdName OBJECT-TYPE
            SYNTAX OCTET STRING (SIZE (1..43))
            MAX-ACCESS not-accessible
            STATUS current
            DESCRIPTION
                "
                This object indicates the name of the Maintenance Domain.
                "
            ::= { hwDot1agCfmQueryMdIndexEntry 1 }


        hwDot1agCfmQueryMdIndex OBJECT-TYPE
            SYNTAX Unsigned32
            MAX-ACCESS read-only
            STATUS current
            DESCRIPTION
                "
                This object indicates the index to the Maintenance Domain table.
                "
            ::= { hwDot1agCfmQueryMdIndexEntry 2 }


        hwDot1agCfmQueryMaIndexTable OBJECT-TYPE
            SYNTAX SEQUENCE OF HwDot1agCfmQueryMaIndexEntry
            MAX-ACCESS not-accessible
            STATUS current
            DESCRIPTION
                "
                This table is used to get the index of the Maintenance Association table.
                "
            ::= { hwDot1agCfmQueryObject 2 }


        hwDot1agCfmQueryMaIndexEntry OBJECT-TYPE
            SYNTAX HwDot1agCfmQueryMaIndexEntry
            MAX-ACCESS not-accessible
            STATUS current
            DESCRIPTION
                "
                The Ma Index table entry.
                "
            INDEX { hwDot1agCfmQueryMdName , hwDot1agCfmQueryMaName}
            ::= { hwDot1agCfmQueryMaIndexTable 1 }


        HwDot1agCfmQueryMaIndexEntry ::=
            SEQUENCE {
                hwDot1agCfmQueryMaName
                    OCTET STRING,
                hwDot1agCfmQueryMaIndex
                    Unsigned32
             }


        hwDot1agCfmQueryMaName OBJECT-TYPE
            SYNTAX OCTET STRING (SIZE (1..43))
            MAX-ACCESS not-accessible
            STATUS current
            DESCRIPTION
                "
                This object indicates the name of Maintenance Association.
                "
            ::= { hwDot1agCfmQueryMaIndexEntry 1 }


        hwDot1agCfmQueryMaIndex OBJECT-TYPE
            SYNTAX Unsigned32
            MAX-ACCESS read-only
            STATUS current
            DESCRIPTION
                "
                This object indicates the index to the Maintenance Association table.
                "
            ::= { hwDot1agCfmQueryMaIndexEntry 2 }
            
            
        hwDot1agCfmMPAddressModel OBJECT-TYPE
            SYNTAX INTEGER
                {
                bridge(1),
                individual(2)
                }
            MAX-ACCESS read-write
            STATUS current
            DESCRIPTION
                "
                This object indicates the MP address model of the CFM.
                The value of this object can be:
                  bridge: indicates bridge MAC MP address model.
                  individual: indicates individual MP address model.
                "
            ::= { hwEthOam1ag 101 }            


        hwEthOam3ah OBJECT IDENTIFIER ::= { hwEthOamMib 2 }


-- 
-- hwDot3ah
-- 
        hwDot3ahEfmEnabled OBJECT-TYPE
            SYNTAX EnabledStatus
            MAX-ACCESS read-write
            STATUS current
            DESCRIPTION
                "
                Enable the EFM globally.
                "
            ::= { hwEthOam3ah 1 }


--  EfmObject
        hwDot3ahEfmObject OBJECT IDENTIFIER ::= { hwEthOam3ah 2 }


--  DetectModeTable
        hwDot3ahEfmDetectModeTable OBJECT-TYPE
            SYNTAX SEQUENCE OF HwDot3ahEfmDetectModeEntry
            MAX-ACCESS not-accessible
            STATUS current
            DESCRIPTION
                "
                Set the detection mode table in the last one kilometer on the interface.
                "
            ::= { hwDot3ahEfmObject 1 }


        hwDot3ahEfmDetectModeEntry OBJECT-TYPE
            SYNTAX HwDot3ahEfmDetectModeEntry
            MAX-ACCESS not-accessible
            STATUS current
            DESCRIPTION
                "
                Set the detection mode entity in the last one kilometer on the interface.
                "
            AUGMENTS { hwDot3ahEfmEntry }
            ::= { hwDot3ahEfmDetectModeTable 1 }


        HwDot3ahEfmDetectModeEntry ::=
            SEQUENCE {
                hwDot3ahEfmDetectMode
                    HWDetectType,
                hwDot3ahEfmDetectInterval
                    TimeInterval,
                hwDot3ahEfmDetectMalfunction
                    Integer32
             }

        hwDot3ahEfmDetectMode OBJECT-TYPE
            SYNTAX HWDetectType
            MAX-ACCESS read-write
            STATUS current
            DESCRIPTION
                "
                Detection mode ( fast detection and standard detection)
                "
            DEFVAL { normalDetect }
            ::= { hwDot3ahEfmDetectModeEntry 11 }


        hwDot3ahEfmDetectInterval OBJECT-TYPE
            SYNTAX TimeInterval
            MAX-ACCESS read-write
            STATUS current
            DESCRIPTION
                "
                Time interval of detection
                "
            ::= { hwDot3ahEfmDetectModeEntry 12 }


        hwDot3ahEfmDetectMalfunction OBJECT-TYPE
            SYNTAX Integer32 (0..768)
            MAX-ACCESS read-only
            STATUS current
            DESCRIPTION
                "
                Failure description from 802.3ah and from associated modules.
                "
            ::= { hwDot3ahEfmDetectModeEntry 13 }


--  ***************************************************************
--
-- Ethernet OAM Control group
--
        hwDot3ahEfmTable OBJECT-TYPE
            SYNTAX SEQUENCE OF HwDot3ahEfmEntry
            MAX-ACCESS not-accessible
            STATUS current
            DESCRIPTION
                "This table contains the primary controls and status for the
                OAM capabilities of an Ethernet like interface.  There will be
                one row in this table for each Ethernet like interface in the
                system that supports the OAM functions defined in [802.3ah].
                "
            ::= { hwDot3ahEfmObject 2 }


        hwDot3ahEfmEntry OBJECT-TYPE
            SYNTAX HwDot3ahEfmEntry
            MAX-ACCESS not-accessible
            STATUS current
            DESCRIPTION
                "An entry in the table, containing information on the Ethernet
                OAM function for a single Ethernet like interface. Entries in
                the table are created automatically for each interface
                supporting Ethernet OAM. The status of the row entry can be
                determined from hwDot3ahEfmOperStatus.

                A hwDot3ahEfmEntry is indexed in the hwDot3ahEfmTable by the ifIndex
                object of the Interfaces MIB.
                "
            INDEX { ifIndex }
            ::= { hwDot3ahEfmTable 1 }


        HwDot3ahEfmEntry ::=
            SEQUENCE {
                hwDot3ahEfmAdminState
                    EnabledStatus,
                hwDot3ahEfmOperStatus
                    INTEGER,
                hwDot3ahEfmMode
                    INTEGER,
                hwDot3ahEfmMaxOamPduSize
                    Unsigned32,
                hwDot3ahEfmConfigRevision
                    Unsigned32,
                hwDot3ahEfmFunctionsSupported
                    BITS,
                hwDot3ahEfmTimeout
                    Unsigned32,     
                hwDot3ahEfmInterval
                    Unsigned32
                    
             }

        hwDot3ahEfmAdminState OBJECT-TYPE
            SYNTAX EnabledStatus
            MAX-ACCESS read-write
            STATUS current
            DESCRIPTION
                "This object is used to provision the default administrative
                OAM mode for this interface.  This object represents the
                desired state of OAM for this interface.

                The hwDot3ahEfmAdminState always starts in the disabled(2) state
                until an explicit management action or configuration
                information retained by the system causes a transition to the
                enabled(2) state.   When enabled(1), Ethernet OAM will attempt
                to operate over this interface.
                "
            REFERENCE
                "[802.3ah], 30.3.6.1.2"
            ::= { hwDot3ahEfmEntry 1 }


        hwDot3ahEfmOperStatus OBJECT-TYPE
            SYNTAX INTEGER
                {
                disabled(1),
                linkFault(2),
                passiveWait(3),
                activeSendLocal(4),
                sendLocalAndRemote(5),
                sendLocalAndRemoteOk(6),
                oamPeeringLocallyRejected(7),
                oamPeeringRemotelyRejected(8),
                operational(9),
                nonOperHalfDuplex(10)
                }
            MAX-ACCESS read-only
            STATUS current
            DESCRIPTION
                "At initialization and failure conditions, two OAM entities on
                the same full-duplex Ethernet link begin a discovery phase to
                determine what OAM capabilities may be used on that link.
                "
            REFERENCE
                "[802.3ah], 30.3.6.1.4, 30.3.6.1.10, 30.3.6.1.11"
            ::= { hwDot3ahEfmEntry 2 }


        hwDot3ahEfmMode OBJECT-TYPE
            SYNTAX INTEGER
                {
                active(1),
                passive(2)
                }
            MAX-ACCESS read-write
            STATUS current
            DESCRIPTION
                "This object configures the mode of OAM operation for this
                Ethernet like interface.  OAM on Ethernet interfaces may be in
                'active' mode or 'passive' mode.
                "
            REFERENCE
                "[802.3ah], 30.3.6.1.3"
            ::= { hwDot3ahEfmEntry 3 }


        hwDot3ahEfmMaxOamPduSize OBJECT-TYPE
            SYNTAX Unsigned32 (64..1518)
            UNITS "octets"
            MAX-ACCESS read-only
            STATUS current
            DESCRIPTION
                "The largest OAMPDU that the OAM entity supports.  OAM
                entities exchange maximum OAMPDU sizes and negotiate to use
                the smaller of the two maximum OAMPDU sizes between the peers.
                This value is determined by the local implementation.
                "
            REFERENCE
                "[802.3ah], 30.3.6.1.8"
            ::= { hwDot3ahEfmEntry 4 }


        hwDot3ahEfmConfigRevision OBJECT-TYPE
            SYNTAX Unsigned32 (0..65535)
            MAX-ACCESS read-only
            STATUS current
            DESCRIPTION
                "The configuration revision of the OAM entity as reflected in
                the latest OAMPDU sent by the OAM entity.  The config revision
                is used by OAM entities to indicate configuration changes have
                occurred which might require the peer OAM entity to
                re-evaluate whether OAM peering is allowed.
                "
            REFERENCE
                "[802.3ah], 30.3.6.1.12"
            ::= { hwDot3ahEfmEntry 5 }


        hwDot3ahEfmFunctionsSupported OBJECT-TYPE
            SYNTAX BITS
                {
                unidirectionalSupport(0),
                loopbackSupport(1),
                eventSupport(2),
                variableSupport(3)
                }
            MAX-ACCESS read-only
            STATUS current
            DESCRIPTION
                "The OAM functions supported on this Ethernet like interface.
                OAM consists of separate functional sets beyond the basic
                discovery process which is always required.  These functional
                groups can be supported independently by any implementation.
                These values are communicated to the peer via the local
                configuration field of Information OAMPDUs.

                Setting 'unidirectionalSupport(0)' indicates that the OAM
                entity supports the transmission of OAMPDUs on links that are
                operating in unidirectional mode (traffic flowing in one
                direction only).  Setting 'loopbackSupport(1)' indicates the
                OAM entity can initiate and respond to loopback commands.
                Setting 'eventSupport(2)' indicates the OAM entity can send
                and receive Event Notification OAMPDUs. Setting
                'variableSupport(3)' indicates the OAM entity can send and
                receive Variable Request and Response OAMPDUs.
                "
            REFERENCE
                "[802.3ah], 30.3.6.1.6"
            ::= { hwDot3ahEfmEntry 6 }
            
      hwDot3ahEfmTimeout OBJECT-TYPE
            SYNTAX Unsigned32 (300..30000)               
            UNITS "milliseconds"         
            MAX-ACCESS read-write
            STATUS current
            DESCRIPTION
                "The EFM Timeout object defines the max time that the EFM session 
                 stays in detect mode since the last OAMPDU received. if there's
                 no OAMPDU received within the time the timeout value defines, the
                 EFM session will turn into discovery state. 
                 
                 The value of EFM Timeout should be three or more times the value of 
                 the sending interval of the peer interface.
                 
                 The timeout value must be an exact integral multiple of 100.
                 
                 Range: 300-30000
                 Default: 5000 
                 Unit: milliseconds         
                "
            REFERENCE
                "[802.3ah]"
            ::= { hwDot3ahEfmEntry 7 }

      hwDot3ahEfmInterval OBJECT-TYPE
            SYNTAX Unsigned32 (100..1000)               
            UNITS "milliseconds"         
            MAX-ACCESS read-write
            STATUS current
            DESCRIPTION
                "The EFM interval object defines the interval of sending OAM PDUs.
                                 
                 The value of EFM interval should be the same as the value of 
                 the peer interface.
                 
                 The interval value must be an exact integral multiple of 100.
                 
                 Range: 100-1000
                 Default: 1000 
                 Unit: milliseconds         
                "
            REFERENCE
                "[802.3ah]"
            ::= { hwDot3ahEfmEntry 8 }


--  ***************************************************************
--
-- Ethernet OAM Peer group
--
        hwDot3ahEfmPeerTable OBJECT-TYPE
            SYNTAX SEQUENCE OF HwDot3ahEfmPeerEntry
            MAX-ACCESS not-accessible
            STATUS current
            DESCRIPTION
                "This table contains information about the OAM peer for a
                particular Ethernet like interface. OAM entities communicate
                with a single OAM peer entity on Ethernet links on which OAM
                is enabled and operating properly.  There is one entry in this
                table for each entry in the hwDot3ahEfmTable for which information
                on the peer OAM entity is available.
                "
            ::= { hwDot3ahEfmObject 3 }


        hwDot3ahEfmPeerEntry OBJECT-TYPE
            SYNTAX HwDot3ahEfmPeerEntry
            MAX-ACCESS not-accessible
            STATUS current
            DESCRIPTION
                "An entry in the table, containing information on the peer OAM
                entity for a single Ethernet like interface.

                Note that there is at most one OAM peer for each Ethernet like
                interface.  Entries are automatically created when information
                about the OAM peer entity becomes available, and automatically
                deleted when the OAM peer entity is no longer in
                communication.  Peer information is not available when
                hwDot3ahEfmOperStatus is disabled(1), linkFault(2),
                passiveWait(3), activeSendLocal(4). or nonOperHalfDuplex(10)).
                "
            INDEX { ifIndex }
            ::= { hwDot3ahEfmPeerTable 1 }


        HwDot3ahEfmPeerEntry ::=
            SEQUENCE {
                hwDot3ahEfmPeerMacAddress
                    OCTET STRING,
                hwDot3ahEfmPeerVendorOui
                    HWDot3Oui,
                hwDot3ahEfmPeerVendorInfo
                    Unsigned32,
                hwDot3ahEfmPeerMode
                    INTEGER,
                hwDot3ahEfmPeerMaxOamPduSize
                    Unsigned32,
                hwDot3ahEfmPeerConfigRevision
                    Unsigned32,
                hwDot3ahEfmPeerFunctionsSupported
                    BITS
             }

        hwDot3ahEfmPeerMacAddress OBJECT-TYPE
            SYNTAX OCTET STRING
            MAX-ACCESS read-only
            STATUS current
            DESCRIPTION
                "The MAC address of the peer OAM entity.  The MAC address is
                derived from the most recently received OAMPDU.
                "
            REFERENCE
                "[802.3ah], 30.3.6.1.5."
            ::= { hwDot3ahEfmPeerEntry 1 }


        hwDot3ahEfmPeerVendorOui OBJECT-TYPE
            SYNTAX HWDot3Oui
            MAX-ACCESS read-only
            STATUS current
            DESCRIPTION
                "The OUI of the OAM peer as reflected in the latest
                Information OAMPDU received with a Local Information TLV.  The
                OUI can be used to identify the vendor of the remote OAM
                entity.  This value is initialized to zero before any Local
                Information TLV is received.
                "
            REFERENCE
                "[802.3ah], 30.3.6.1.16."
            ::= { hwDot3ahEfmPeerEntry 2 }


        hwDot3ahEfmPeerVendorInfo OBJECT-TYPE
            SYNTAX Unsigned32
            MAX-ACCESS read-only
            STATUS current
            DESCRIPTION
                "The Vendor Info of the OAM peer as reflected in the latest
                Information OAMPDU received with a Local Information TLV.  The
                vendor information field is within the Local Information TLV,
                and can be used to determine additional information about the
                peer entity.  The format of the vendor information is
                unspecified within the 32-bit field.  This value is
                initialized to zero before any Local Information TLV is
                received.
                "
            REFERENCE
                "[802.3ah], 30.3.6.1.17."
            ::= { hwDot3ahEfmPeerEntry 3 }


        hwDot3ahEfmPeerMode OBJECT-TYPE
            SYNTAX INTEGER
                {
                active(1),
                passive(2),
                unknown(3)
                }
            MAX-ACCESS read-only
            STATUS current
            DESCRIPTION
                "The mode of the OAM peer as reflected in the latest
                Information OAMPDU received with a Local Information TLV.  The
                mode of the peer can be determined from the Configuration
                field in the Local Information TLV of the last Information
                OAMPDU received from the peer.  The value is unknown(3)
                whenever no Local Information TLV has been received.  The
                values of active(1) and passive(2) are returned when a Local
                Information TLV has been received indicating the peer is in
                active or passive mode, respectively.
                "
            REFERENCE
                "[802.3ah], 30.3.6.1.7."
            ::= { hwDot3ahEfmPeerEntry 4 }


        hwDot3ahEfmPeerMaxOamPduSize OBJECT-TYPE
            SYNTAX Unsigned32 (0..65535)
            UNITS "octets"
            MAX-ACCESS read-only
            STATUS current
            DESCRIPTION
                "The maximum size of OAMPDU supported by the peer as reflected
                in the latest Information OAMPDU received with a Local
                Information TLV.   Ethernet OAM on this interface must not use
                OAMPDUs that exceed this size.  The maximum OAMPDU size can be
                determined from the PDU Configuration field of the Local
                Information TLV of the last Information OAMPDU received from
                the peer.  A value of zero is returned if no Local Information
                TLV has been received.  Otherwise, the value of the OAM peer's
                maximum OAMPDU size is returned in this value.
                Note that the values 1..65534 are invalid sizes for Ethernet
                frames and should never appear.
                "
            REFERENCE
                "[802.3ah], 30.3.6.1.9."
            ::= { hwDot3ahEfmPeerEntry 5 }


        hwDot3ahEfmPeerConfigRevision OBJECT-TYPE
            SYNTAX Unsigned32 (0..65535)
            MAX-ACCESS read-only
            STATUS current
            DESCRIPTION
                "The configuration revision of the OAM peer as reflected in
                the latest OAMPDU.  This attribute is changed by the peer
                whenever it has a local configuration change for Ethernet OAM
                this interface.  The configuration revision can be determined
                from the Revision field of the Local Information TLV of the
                most recently received Information OAMPDU with a Local
                Information TLV. A value of zero is returned if no Local
                Information TLV has been received.
                "
            REFERENCE
                "[802.3ah], 30.3.6.1.13."
            ::= { hwDot3ahEfmPeerEntry 6 }


        hwDot3ahEfmPeerFunctionsSupported OBJECT-TYPE
            SYNTAX BITS
                {
                unidirectionalSupport(0),
                loopbackSupport(1),
                eventSupport(2),
                variableSupport(3)
                }
            MAX-ACCESS read-only
            STATUS current
            DESCRIPTION
                "The OAM functions supported on this Ethernet like interface.
                OAM consists of separate functionality sets above the basic
                discovery process.  This value indicates the capabilities of
                the peer OAM entity with respect to these functions.  This
                value is initialized so all bits are clear.

                If unidirectionalSupport(0) is set, then the peer OAM entity
                supports sending OAM frames on Ethernet interfaces when the
                receive path is known to be inoperable.   If
                loopbackSupport(1) is set, then the peer OAM entity can send
                and receive OAM loopback commands.  If eventSupport(2) is set,
                then the peer OAM entity can send and receive event OAMPDUs to
                signal various error conditions. If variableSupport(3) is set,
                then the peer OAM entity can send and receive variable
                requests to monitor attribute value as described in Clause 57
                of [802.3ah].

                The capabilities of the OAM peer can be determined from the
                configuration field of the Local Information TLV of the most
                recently received Information OAMPDU with a Local Information
                TLV.  All zeros are returned if no Local Information TLV has
                yet been received.
                "
            REFERENCE
                "[802.3ah], REFERENCE 30.3.6.1.7."
            ::= { hwDot3ahEfmPeerEntry 7 }


--  ***************************************************************
--
-- Ethernet OAM Loopback group
--
        hwDot3ahEfmLoopbackTable OBJECT-TYPE
            SYNTAX SEQUENCE OF HwDot3ahEfmLoopbackEntry
            MAX-ACCESS not-accessible
            STATUS current
            DESCRIPTION
                "This table contains controls for the loopback state of the
                local link as well as indicating the status of the loopback
                function.  There is one entry in this table for each entry in
                hwDot3ahEfmTable that supports loopback functionality (where
                hwDot3ahEfmFunctionsSupported includes the loopbackSupport bit
                set).

                Loopback can be used to place the remote OAM entity in a state
                where every received frame (except OAMPDUs) is echoed back
                over the same interface on which they were received.   In this
                state, at the remote entity, 'normal' traffic is disabled as
                only the looped back frames are transmitted on the interface.
                Loopback is thus an intrusive operation that prohibits normal
                data flow and should be used accordingly.  "
            ::= { hwDot3ahEfmObject 4 }


        hwDot3ahEfmLoopbackEntry OBJECT-TYPE
            SYNTAX HwDot3ahEfmLoopbackEntry
            MAX-ACCESS not-accessible
            STATUS current
            DESCRIPTION
                "An entry in the table, containing information on the loopback
                status for a single Ethernet like interface.  Entries in the
                table are automatically created whenever the local OAM entity
                supports loopback capabilities.  The loopback status on the
                interface can be determined from the hwDot3ahEfmLoopbackStatus
                object.
                "
            INDEX { ifIndex }
            ::= { hwDot3ahEfmLoopbackTable 1 }


        HwDot3ahEfmLoopbackEntry ::=
            SEQUENCE {
                hwDot3ahEfmLoopbackStatus
                    INTEGER,
                hwDot3ahEfmLoopbackIgnoreRx
                    INTEGER,
                hwDot3ahEfmLoopbackTimeout
                    Unsigned32
             }

        hwDot3ahEfmLoopbackStatus OBJECT-TYPE
            SYNTAX INTEGER
                {
                noLoopback(1),
                initiatingLoopback (2),
                remoteLoopback(3),
                terminatingLoopback(4),
                localLoopback(5),
                unknown(6)
                }
            MAX-ACCESS read-write
            STATUS current
            DESCRIPTION
                "The loopback status of the OAM entity. When
                operating in normal mode with no loopback in progress, the
                status reads noLoopback(1).
                The values initiatingLooopback(2) and terminatingLoopback(4)
                can be read or written.  The other values can only be read -
                they can never be written.
                "
            REFERENCE
                "[802.3ah], REFERENCE 57.2.11, 30.3.61.14,
                30.3.6.1.15"
            ::= { hwDot3ahEfmLoopbackEntry 1 }


        hwDot3ahEfmLoopbackIgnoreRx OBJECT-TYPE
            SYNTAX INTEGER
                {
                ignore(1),
                process(2)
                }
            MAX-ACCESS read-write
            STATUS current
            DESCRIPTION
                "Since OAM loopback is a disruptive operation (user traffic
                does not pass), this attribute provides a mechanism to provide
                controls over whether received OAM loopback commands are
                processed or ignored.  When the value is ignore(1), received
                loopback commands are ignored.  When the value is process(2),
                OAM loopback commands are processed.  The default value is to
                process loopback commands (process(2)).
                "
            REFERENCE
                "[802.3ah], REFERENCE 57.2.11, 30.3.61.14,
                30.3.6.1.15"   
            DEFVAL { process }       
                        ::= { hwDot3ahEfmLoopbackEntry 2 }


        hwDot3ahEfmLoopbackTimeout OBJECT-TYPE
            SYNTAX Unsigned32 (0..1000)
            UNITS "minutes"
            MAX-ACCESS read-write
            STATUS current
            DESCRIPTION
                "This object specifies the timeout period for a remote loopback. The
                 value ranges from 0 to 1000 in minutes. The default value is 20
                 minutes. 0 indicates that no timeout period is set.
                "
            DEFVAL { 20 }
            ::= { hwDot3ahEfmLoopbackEntry 3 }


--  ***************************************************************
--
-- Ethernet OAM Statistics group
--
        hwDot3ahEfmStatsTable OBJECT-TYPE
            SYNTAX SEQUENCE OF HwDot3ahEfmStatsEntry
            MAX-ACCESS not-accessible
            STATUS current
            DESCRIPTION
                "This table contains statistics for the OAM function on a
                particular Ethernet like interface. There is an entry in the
                table for every entry in the hwDot3ahEfmTable.

                The counters in this table are defined as 32-bit entries to
                match the counter size as defined in [802.3ah].  Given the OAM
                protocol is a slow protocol, the counters increment at a slow
                rate.
                "
            ::= { hwDot3ahEfmObject 5 }


        hwDot3ahEfmStatsEntry OBJECT-TYPE
            SYNTAX HwDot3ahEfmStatsEntry
            MAX-ACCESS not-accessible
            STATUS current
            DESCRIPTION
                "An entry in the table, containing statistics information on
                the Ethernet OAM function for a single Ethernet like
                interface.  Entries are automatically created for every entry
                in the hwDot3ahEfmTable.  Counters are maintained across
                transitions in hwDot3ahEfmOperStatus.
                "
            INDEX { ifIndex }
            ::= { hwDot3ahEfmStatsTable 1 }


        HwDot3ahEfmStatsEntry ::=
            SEQUENCE {
                hwDot3ahEfmInformationTx
                    Counter32,
                hwDot3ahEfmInformationRx
                    Counter32,
                hwDot3ahEfmUniqueEventNotificationTx
                    Counter32,
                hwDot3ahEfmUniqueEventNotificationRx
                    Counter32,
                hwDot3ahEfmDuplicateEventNotificationTx
                    Counter32,
                hwDot3ahEfmDuplicateEventNotificationRx
                    Counter32,
                hwDot3ahEfmLoopbackControlTx
                    Counter32,
                hwDot3ahEfmLoopbackControlRx
                    Counter32,
                hwDot3ahEfmVariableRequestTx
                    Counter32,
                hwDot3ahEfmVariableRequestRx
                    Counter32,
                hwDot3ahEfmVariableResponseTx
                    Counter32,
                hwDot3ahEfmVariableResponseRx
                    Counter32,
                hwDot3ahEfmOrgSpecificTx
                    Counter32,
                hwDot3ahEfmOrgSpecificRx
                    Counter32,
                hwDot3ahEfmUnsupportedCodesTx
                    Counter32,
                hwDot3ahEfmUnsupportedCodesRx
                    Counter32,
                hwDot3ahEfmFramesLostDueToOam
                    Counter32
             }

        hwDot3ahEfmInformationTx OBJECT-TYPE
            SYNTAX Counter32
            UNITS "frames"
            MAX-ACCESS read-only
            STATUS current
            DESCRIPTION
                "A count of the number of Information OAMPDUs transmitted on
                this interface.

                Discontinuities of this counter can occur at re-initialization
                of the management system, and at other times as indicated by
                the value of the ifCounterDiscontinuityTime.  "
            REFERENCE
                "[802.3ah], 30.3.6.1.20."
            ::= { hwDot3ahEfmStatsEntry 1 }


        hwDot3ahEfmInformationRx OBJECT-TYPE
            SYNTAX Counter32
            UNITS "frames"
            MAX-ACCESS read-only
            STATUS current
            DESCRIPTION
                "A count of the number of Information OAMPDUs received on this
                interface.

                Discontinuities of this counter can occur at re-initialization
                of the management system, and at other times as indicated by
                the value of the ifCounterDiscontinuityTime.
                "
            REFERENCE
                "[802.3ah], 30.3.6.1.21."
            ::= { hwDot3ahEfmStatsEntry 2 }


        hwDot3ahEfmUniqueEventNotificationTx OBJECT-TYPE
            SYNTAX Counter32
            UNITS "frames"
            MAX-ACCESS read-only
            STATUS current
            DESCRIPTION
                "A count of the number of unique Event OAMPDUs transmitted on
                this interface.  Event notifications may be sent in duplicate
                to increase the probability of successfully being received,
                given the possibility that a frame may be lost in transit.
                Duplicate Event Notification transmissions are counted by
                hwDot3ahEfmDuplicateEventNotificationTx.

                A unique Event Notification OAMPDU is indicated as an Event
                Notification OAMPDU with a Sequence Number field that is
                distinct from the previously transmitted Event Notification
                OAMPDU Sequence Number.

                Discontinuities of this counter can occur at re-initialization
                of the management system, and at other times as indicated by
                the value of the ifCounterDiscontinuityTime.
                "
            REFERENCE
                "[802.3ah], 30.3.6.1.22."
            ::= { hwDot3ahEfmStatsEntry 3 }


        hwDot3ahEfmUniqueEventNotificationRx OBJECT-TYPE
            SYNTAX Counter32
            UNITS "frames"
            MAX-ACCESS read-only
            STATUS current
            DESCRIPTION
                "A count of the number of unique Event OAMPDUs received on
                this interface.  Event notification OAMPDUs may be sent in
                duplicate to increase the probability of successfully being
                received, given the possibility that a frame may be lost in
                transit.  Duplicate Event Notification receptions are counted
                by hwDot3ahEfmDuplicateEventNotificationRx.

                A unique Event Notification OAMPDU is indicated as an Event
                Notification OAMPDU with a Sequence Number field that is
                distinct from the previously received Event Notification
                OAMPDU Sequence Number.

                Discontinuities of this counter can occur at re-initialization
                of the management system, and at other times as indicated by
                the value of the ifCounterDiscontinuityTime.
                "
            REFERENCE
                "[802.3ah], 30.3.6.1.24."
            ::= { hwDot3ahEfmStatsEntry 4 }


        hwDot3ahEfmDuplicateEventNotificationTx OBJECT-TYPE
            SYNTAX Counter32
            UNITS "frames"
            MAX-ACCESS read-only
            STATUS current
            DESCRIPTION
                "A count of the number of duplicate Event OAMPDUs transmitted
                on this interface.  Event notification OAMPDUs may be sent in
                duplicate to increase the probability of successfully being
                received, given the possibility that a frame may be lost in
                transit.

                A duplicate Event Notification OAMPDU is indicated as an Event
                Notification OAMPDU with a Sequence Number field that is
                identical to the previously transmitted Event Notification
                OAMPDU Sequence Number.

                Discontinuities of this counter can occur at re-initialization
                of the management system, and at other times as indicated by
                the value of the ifCounterDiscontinuityTime.
                "
            REFERENCE
                "[802.3ah], 30.3.6.1.23."
            ::= { hwDot3ahEfmStatsEntry 5 }


        hwDot3ahEfmDuplicateEventNotificationRx OBJECT-TYPE
            SYNTAX Counter32
            UNITS "frames"
            MAX-ACCESS read-only
            STATUS current
            DESCRIPTION
                "A count of the number of duplicate Event OAMPDUs received on
                this interface.  Event notification OAMPDUs may be sent in
                duplicate to increase the probability of successfully being
                received, given the possibility that a frame may be lost in
                transit.

                A duplicate Event Notification OAMPDU is indicated as an Event
                Notification OAMPDU with a Sequence Number field that is
                identical to the previously received Event Notification OAMPDU
                Sequence Number.

                Discontinuities of this counter can occur at re-initialization
                of the management system, and at other times as indicated by
                the value of the ifCounterDiscontinuityTime.
                "
            REFERENCE
                "[802.3ah], 30.3.6.1.25."
            ::= { hwDot3ahEfmStatsEntry 6 }


        hwDot3ahEfmLoopbackControlTx OBJECT-TYPE
            SYNTAX Counter32
            UNITS "frames"
            MAX-ACCESS read-only
            STATUS current
            DESCRIPTION
                "A count of the number of Loopback Control OAMPDUs transmitted
                on this interface.

                Discontinuities of this counter can occur at re-initialization
                of the management system, and at other times as indicated by
                the value of the ifCounterDiscontinuityTime.
                "
            REFERENCE
                "[802.3ah], 30.3.6.1.26."
            ::= { hwDot3ahEfmStatsEntry 7 }


        hwDot3ahEfmLoopbackControlRx OBJECT-TYPE
            SYNTAX Counter32
            UNITS "frames"
            MAX-ACCESS read-only
            STATUS current
            DESCRIPTION
                "A count of the number of Loopback Control OAMPDUs received
                on this interface.

                Discontinuities of this counter can occur at re-initialization
                of the management system, and at other times as indicated by
                the value of the ifCounterDiscontinuityTime.
                "
            REFERENCE
                "[802.3ah], 30.3.6.1.27."
            ::= { hwDot3ahEfmStatsEntry 8 }


        hwDot3ahEfmVariableRequestTx OBJECT-TYPE
            SYNTAX Counter32
            UNITS "frames"
            MAX-ACCESS read-only
            STATUS current
            DESCRIPTION
                "A count of the number of Variable Request OAMPDUs transmitted
                on this interface.

                Discontinuities of this counter can occur at re-initialization
                of the management system, and at other times as indicated by
                the value of the ifCounterDiscontinuityTime.
                "
            REFERENCE
                "[802.3ah], 30.3.6.1.28."
            ::= { hwDot3ahEfmStatsEntry 9 }


        hwDot3ahEfmVariableRequestRx OBJECT-TYPE
            SYNTAX Counter32
            UNITS "frames"
            MAX-ACCESS read-only
            STATUS current
            DESCRIPTION
                "A count of the number of Variable Request OAMPDUs received on
                this interface.

                Discontinuities of this counter can occur at re-initialization
                of the management system, and at other times as indicated by
                the value of the ifCounterDiscontinuityTime.
                "
            REFERENCE
                "[802.3ah], 30.3.6.1.29."
            ::= { hwDot3ahEfmStatsEntry 10 }


        hwDot3ahEfmVariableResponseTx OBJECT-TYPE
            SYNTAX Counter32
            UNITS "frames"
            MAX-ACCESS read-only
            STATUS current
            DESCRIPTION
                "A count of the number of Variable Response OAMPDUs
                transmitted on this interface.

                Discontinuities of this counter can occur at re-initialization
                of the management system, and at other times as indicated by
                the value of the ifCounterDiscontinuityTime.
                "
            REFERENCE
                "[802.3ah], 30.3.6.1.30."
            ::= { hwDot3ahEfmStatsEntry 11 }


        hwDot3ahEfmVariableResponseRx OBJECT-TYPE
            SYNTAX Counter32
            UNITS "frames"
            MAX-ACCESS read-only
            STATUS current
            DESCRIPTION
                "A count of the number of Variable Response OAMPDUs received
                on this interface.

                Discontinuities of this counter can occur at re-initialization
                of the management system, and at other times as indicated by
                the value of the ifCounterDiscontinuityTime.
                "
            REFERENCE
                "[802.3ah], 30.3.6.1.31."
            ::= { hwDot3ahEfmStatsEntry 12 }


        hwDot3ahEfmOrgSpecificTx OBJECT-TYPE
            SYNTAX Counter32
            UNITS "frames"
            MAX-ACCESS read-only
            STATUS current
            DESCRIPTION
                "A count of the number of Organization Specific OAMPDUs
                transmitted on this interface.

                Discontinuities of this counter can occur at re-initialization
                of the management system, and at other times as indicated by
                the value of the ifCounterDiscontinuityTime.
                "
            REFERENCE
                "[802.3ah], 30.3.6.1.32."
            ::= { hwDot3ahEfmStatsEntry 13 }


        hwDot3ahEfmOrgSpecificRx OBJECT-TYPE
            SYNTAX Counter32
            UNITS "frames"
            MAX-ACCESS read-only
            STATUS current
            DESCRIPTION
                "A count of the number of Organization Specific OAMPDUs
                received on this interface.

                Discontinuities of this counter can occur at re-initialization
                of the management system, and at other times as indicated by
                the value of the ifCounterDiscontinuityTime.
                "
            REFERENCE
                "[802.3ah], 30.3.6.1.33."
            ::= { hwDot3ahEfmStatsEntry 14 }


        hwDot3ahEfmUnsupportedCodesTx OBJECT-TYPE
            SYNTAX Counter32
            UNITS "frames"
            MAX-ACCESS read-only
            STATUS current
            DESCRIPTION
                "A count of the number of OAMPDUs transmitted on this
                interface with an unsupported op-code.

                Discontinuities of this counter can occur at re-initialization
                of the management system, and at other times as indicated by
                the value of the ifCounterDiscontinuityTime.
                "
            REFERENCE
                "[802.3ah], 30.3.6.1.18."
            ::= { hwDot3ahEfmStatsEntry 15 }


        hwDot3ahEfmUnsupportedCodesRx OBJECT-TYPE
            SYNTAX Counter32
            UNITS "frames"
            MAX-ACCESS read-only
            STATUS current
            DESCRIPTION
                "A count of the number of OAMPDUs received on this interface
                with an unsupported op-code.

                Discontinuities of this counter can occur at re-initialization
                of the management system, and at other times as indicated by
                the value of the ifCounterDiscontinuityTime.
                "
            REFERENCE
                "[802.3ah], 30.3.6.1.19."
            ::= { hwDot3ahEfmStatsEntry 16 }


        hwDot3ahEfmFramesLostDueToOam OBJECT-TYPE
            SYNTAX Counter32
            UNITS "frames"
            MAX-ACCESS read-only
            STATUS current
            DESCRIPTION
                "A count of the number of frames that were dropped by the OAM
                multiplexer.  Since the OAM multiplexer has multiple inputs
                and a single output, there may be cases where frames are
                dropped due to transmit resource contention.  This counter is
                incremented whenever a frame is dropped by the OAM layer.
                Note that any Ethernet frame, not just OAMPDUs, may be dropped
                by the OAM layer.  This can occur when an OAMPDU takes
                precedence over a 'normal' frame resulting in the 'normal'
                frame being dropped.

                When this counter is incremented, no other counters in this
                MIB are incremented.

                Discontinuities of this counter can occur at re-initialization
                of the management system, and at other times as indicated by
                the value of the ifCounterDiscontinuityTime.
                "
            REFERENCE
                "[802.3ah], 30.3.6.1.46."
            ::= { hwDot3ahEfmStatsEntry 17 }


--  ***************************************************************
--
-- Ethernet OAM Event Configuration group
--
        hwDot3ahEfmEventConfigTable OBJECT-TYPE
            SYNTAX SEQUENCE OF HwDot3ahEfmEventConfigEntry
            MAX-ACCESS not-accessible
            STATUS current
            DESCRIPTION
                "Ethernet OAM includes the ability to generate and receive
                Event Notification OAMPDUs to indicate various link problems.
                This table contains the mechanisms to enable Event
                Notifications and configure the thresholds to generate the
                standard Ethernet OAM events.  There is one entry in the table
                for every entry in hwDot3ahEfmTable that supports OAM events
                (where hwDot3ahEfmFunctionsSupported includes the eventSupport
                bit set). The values in the table are maintained across
                changes to hwDot3ahEfmOperStatus.

                The standard threshold crossing events are:
                  - Errored Symbol Period Event.  Generated when the number of
                    symbol errors exceeds a threshold within a given window
                    defined by a number of symbols (for example, 1,000 symbols
                    out of 1,000,000 had errors).
                  - Errored Frame Period Event.  Generated when the number of
                    frame errors exceeds a threshold within a given window
                    defined by a number of frames (for example, 10 frames out
                    of 1000 had errors).
                  - Errored Frame Event.  Generated when the number of frame
                    errors exceeds a threshold within a given window defined
                    by a period of time (for example, 10 frames in 1 second
                    had errors).
                  - Errored Frame Seconds Summary Event.  Generated when the
                    number of errored frame seconds exceeds a threshold within
                    a given time period (for example, 10 errored frame seconds
                    within the last 100 seconds).  An errored frame second is
                    defined as a 1 second interval which had >0 frame errors.
                There are other events (dying gasp, critical events) that are
                not threshold crossing events but which can be
                enabled/disabled via this table.
                "
            ::= { hwDot3ahEfmObject 6 }


        hwDot3ahEfmEventConfigEntry OBJECT-TYPE
            SYNTAX HwDot3ahEfmEventConfigEntry
            MAX-ACCESS not-accessible
            STATUS current
            DESCRIPTION
                "Entries are automatically created and deleted from this
                table, and exist whenever the OAM entity supports Ethernet OAM
                events (as indicated by the eventSupport bit in
                hwDot3ahEfmFunctionsSuppported).  Values in the table are
                maintained across changes to the value of hwDot3ahEfmOperStatus.

                Event configuration controls when the local management entity
                sends Event Notification OAMPDUs to its OAM peer, and when
                certain event flags are set or cleared in OAMPDUs.
                "
            INDEX { ifIndex }
            ::= { hwDot3ahEfmEventConfigTable 1 }


        HwDot3ahEfmEventConfigEntry ::=
            SEQUENCE {
                hwDot3ahEfmErrSymPeriodWindowHi
                    Unsigned32,
                hwDot3ahEfmErrSymPeriodWindowLo
                    Unsigned32,
                hwDot3ahEfmErrSymPeriodThresholdHi
                    Unsigned32,
                hwDot3ahEfmErrSymPeriodThresholdLo
                    Unsigned32,
                hwDot3ahEfmErrSymPeriodEvNotifEnable
                    TruthValue,
                hwDot3ahEfmErrFramePeriodWindow
                    Unsigned32,
                hwDot3ahEfmErrFramePeriodThreshold
                    Unsigned32,
                hwDot3ahEfmErrFramePeriodEvNotifEnable
                    TruthValue,
                hwDot3ahEfmErrFrameWindow
                    Unsigned32,
                hwDot3ahEfmErrFrameThreshold
                    Unsigned32,
                hwDot3ahEfmErrFrameEvNotifEnable
                    TruthValue,
                hwDot3ahEfmErrFrameSecsSummaryWindow
                    Integer32,
                hwDot3ahEfmErrFrameSecsSummaryThreshold
                    Integer32,
                hwDot3ahEfmErrFrameSecsEvNotifEnable
                    TruthValue,
                hwDot3ahEfmDyingGaspEnable
                    TruthValue,
                hwDot3ahEfmCriticalEventEnable
                    TruthValue,
                hwDot3ahEfmThresholdTriggerErrDown
                    EnabledStatus
             }

        hwDot3ahEfmErrSymPeriodWindowHi OBJECT-TYPE
            SYNTAX Unsigned32
            UNITS "2^32 symbols"
            MAX-ACCESS read-write
            STATUS current
            DESCRIPTION
                "The two objects hwDot3ahEfmErrSymPeriodWindowHi and
                hwDot3ahEfmErrSymPeriodWindowLo together form an unsigned 64-bit
                integer representing the number of symbols over which this
                threshold event is defined.  This is defined as

                hwDot3ahEfmErrSymPeriodWindow = ((2^32)*hwDot3ahEfmErrSymPeriodWindowHi)
                                                + hwDot3ahEfmErrSymPeriodWindowLo

                If hwDot3ahEfmErrSymPeriodThreshold symbol errors occur within a
                window of hwDot3ahEfmErrSymPeriodWindow symbols, an Event
                Notification OAMPDU should be generated with an Errored Symbol
                Period Event TLV indicating the threshold has been crossed in
                this window.

                The default value for hwDot3ahEfmErrSymPeriodWindow is the number
                of symbols in one second for the underlying physical layer.
                "
            REFERENCE
                "[802.3ah], 30.3.6.1.34"
            ::= { hwDot3ahEfmEventConfigEntry 1 }


        hwDot3ahEfmErrSymPeriodWindowLo OBJECT-TYPE
            SYNTAX Unsigned32
            UNITS "symbols"
            MAX-ACCESS read-write
            STATUS current
            DESCRIPTION
                "The two objects hwDot3ahEfmErrSymPeriodWindowHi and
                hwDot3ahEfmErrSymPeriodWindowLo together form an unsigned 64-bit
                integer representing the number of symbols over which this
                threshold event is defined.  This is defined as

                hwDot3ahEfmErrSymPeriodWindow = ((2^32)*hwDot3ahEfmErrSymPeriodWindowHi)
                                                + hwDot3ahEfmErrSymPeriodWindowLo

                If hwDot3ahEfmErrSymPeriodThreshold symbol errors occur within a
                window of hwDot3ahEfmErrSymPeriodWindow symbols, an Event
                Notification OAMPDU should be generated with an Errored Symbol
                Period Event TLV indicating the threshold has been crossed in
                this window.

                The default value for hwDot3ahEfmErrSymPeriodWindow is the number
                of symbols in one second for the underlying physical layer.
                "
            REFERENCE
                "[802.3ah], 30.3.6.1.34"
            ::= { hwDot3ahEfmEventConfigEntry 2 }


        hwDot3ahEfmErrSymPeriodThresholdHi OBJECT-TYPE
            SYNTAX Unsigned32
            UNITS "2^32 symbols"
            MAX-ACCESS read-write
            STATUS current
            DESCRIPTION
                "The two objects hwDot3ahEfmErrSymPeriodThresholdHi and
                hwDot3ahEfmErrSymPeriodThresholdLo together form an unsigned
                64-bit integer representing the number of symbol errors that
                must occur within a given window to cause this event.

                This is defined as

                  hwDot3ahEfmErrSymPeriodThreshold =
                                    ((2^32) * hwDot3ahEfmErrSymPeriodThresholdHi)
                                            + hwDot3ahEfmErrSymPeriodThresholdLo

                If hwDot3ahEfmErrSymPeriodThreshold symbol errors occur within a
                window of hwDot3ahEfmErrSymPeriodWindow symbols, an Event
                Notification OAMPDU should be generated with an Errored Symbol
                Period Event TLV indicating the threshold has been crossed in
                this window.

                The default value for hwDot3ahEfmErrSymPeriodThreshold is one
                symbol errors.  If the threshold value is zero, then an Event
                Notification OAMPDU is sent periodically (at the end of every
                window).  This can be used as an asynchronous notification to
                the peer OAM entity of the statistics related to this
                threshold crossing alarm.
                "
            REFERENCE
                "[802.3ah], 30.3.6.1.34"
            ::= { hwDot3ahEfmEventConfigEntry 3 }


        hwDot3ahEfmErrSymPeriodThresholdLo OBJECT-TYPE
            SYNTAX Unsigned32
            UNITS "symbols"
            MAX-ACCESS read-write
            STATUS current
            DESCRIPTION
                "The two objects hwDot3ahEfmErrSymPeriodThresholdHi and
                hwDot3ahEfmErrSymPeriodThresholdLo together form an unsigned
                64-bit integer representing the number of symbol errors that
                must occur within a given window to cause this event.

                This is defined as

                  hwDot3ahEfmErrSymPeriodThreshold =
                                    ((2^32) * hwDot3ahEfmErrSymPeriodThresholdHi)
                                            + hwDot3ahEfmErrSymPeriodThresholdLo

                If hwDot3ahEfmErrSymPeriodThreshold symbol errors occur within a
                window of hwDot3ahEfmErrSymPeriodWindow symbols, an Event
                Notification OAMPDU should be generated with an Errored Symbol
                Period Event TLV indicating the threshold has been crossed in
                this window.

                The default value for hwDot3ahEfmErrSymPeriodThreshold is one
                symbol error. If the threshold value is zero, then an Event
                Notification OAMPDU is sent periodically (at the end of every
                window).  This can be used as an asynchronous notification to
                the peer OAM entity of the statistics related to this
                threshold crossing alarm.
                "
            REFERENCE
                "[802.3ah], 30.3.6.1.34"
            ::= { hwDot3ahEfmEventConfigEntry 4 }


        hwDot3ahEfmErrSymPeriodEvNotifEnable OBJECT-TYPE
            SYNTAX TruthValue
            MAX-ACCESS read-write
            STATUS current
            DESCRIPTION
                "If true, the OAM entity should send an Event Notification
                OAMPDU when an Errored Symbol Period Event occurs.
                By default, this object should have the value true for
                Ethernet like interfaces that support OAM.  If the OAM layer
                does not support event notifications (as indicated via the
                hwDot3ahEfmFunctionsSupported attribute), this value is ignored.
                "
            ::= { hwDot3ahEfmEventConfigEntry 5 }


        hwDot3ahEfmErrFramePeriodWindow OBJECT-TYPE
            SYNTAX Unsigned32
            UNITS "frames"
            MAX-ACCESS read-write
            STATUS current
            DESCRIPTION
                "The number of frames over which the threshold is defined.
                The default value of the window is the number of minimum size
                Ethernet frames that can be received over the physical layer
                in one second.

                If hwDot3ahEfmErrFramePeriodThreshold frame errors occur within a
                window of hwDot3ahEfmErrFramePeriodWindow frames, an Event
                Notification OAMPDU should be generated with an Errored Frame
                Period Event TLV indicating the threshold has been crossed in
                this window.
                "
            REFERENCE
                "[802.3ah], 30.3.6.1.38"
            ::= { hwDot3ahEfmEventConfigEntry 6 }


        hwDot3ahEfmErrFramePeriodThreshold OBJECT-TYPE
            SYNTAX Unsigned32
            UNITS "frames"
            MAX-ACCESS read-write
            STATUS current
            DESCRIPTION
                "The number of frame errors that must occur for this event to
                be triggered.  The default value is one frame error.  If the
                threshold value is zero, then an Event Notification OAMPDU is
                sent periodically (at the end of every window).  This can be
                used as an asynchronous notification to the peer OAM entity of
                the statistics related to this threshold crossing alarm.

                If hwDot3ahEfmErrFramePeriodThreshold frame errors occur within a
                window of hwDot3ahEfmErrFramePeriodWindow frames, an Event
                Notification OAMPDU should be generated with an Errored Frame
                Period Event TLV indicating the threshold has been crossed in
                this window.
                "
            REFERENCE
                "[802.3ah], 30.3.6.1.38"
            ::= { hwDot3ahEfmEventConfigEntry 7 }


        hwDot3ahEfmErrFramePeriodEvNotifEnable OBJECT-TYPE
            SYNTAX TruthValue
            MAX-ACCESS read-write
            STATUS current
            DESCRIPTION
                "If true, the OAM entity should send an Event Notification
                OAMPDU when an Errored Frame Period Event occurs.

                By default, this object should have the value true for
                Ethernet like interfaces that support OAM.  If the OAM layer
                does not support event notifications (as indicated via the
                hwDot3ahEfmFunctionsSupported attribute), this value is ignored.
                "
            ::= { hwDot3ahEfmEventConfigEntry 8 }


        hwDot3ahEfmErrFrameWindow OBJECT-TYPE
            SYNTAX Unsigned32
            UNITS "tenths of a second"
            MAX-ACCESS read-write
            STATUS current
            DESCRIPTION
                "The amount of time (in 100ms increments) over which the
                threshold is defined.  The default value is 10 (1 second).

                If hwDot3ahEfmErrFrameThreshold frame errors occur within a window
                of hwDot3ahEfmErrFrameWindow seconds (measured in tenths of
                seconds), an Event Notification OAMPDU should be generated
                with an Errored Frame Event TLV indicating the threshold has
                been crossed in this window.
                "
            REFERENCE
                "[802.3ah], 30.3.6.1.36"
            ::= { hwDot3ahEfmEventConfigEntry 9 }


        hwDot3ahEfmErrFrameThreshold OBJECT-TYPE
            SYNTAX Unsigned32
            UNITS "frames"
            MAX-ACCESS read-write
            STATUS current
            DESCRIPTION
                "The number of frame errors that must occur for this event to
                be triggered.  The default value is one frame error. If the
                threshold value is zero, then an Event Notification OAMPDU is
                sent periodically (at the end of every window).  This can be
                used as an asynchronous notification to the peer OAM entity of
                the statistics related to this threshold crossing alarm.

                If hwDot3ahEfmErrFrameThreshold frame errors occur within a window
                of hwDot3ahEfmErrFrameWindow (in tenths of seconds), an Event
                Notification OAMPDU should be generated with an Errored Frame
                Event TLV indicating the threshold has been crossed in this
                window.
                "
            REFERENCE
                "[802.3ah], 30.3.6.1.36"
            ::= { hwDot3ahEfmEventConfigEntry 10 }


        hwDot3ahEfmErrFrameEvNotifEnable OBJECT-TYPE
            SYNTAX TruthValue
            MAX-ACCESS read-write
            STATUS current
            DESCRIPTION
                "If true, the OAM entity should send an Event Notification
                OAMPDU when an Errored Frame Event occurs.

                By default, this object should have the value true for
                Ethernet like interfaces that support OAM.  If the OAM layer
                does not support event notifications (as indicated via the
                hwDot3ahEfmFunctionsSupported attribute), this value is ignored.
                "
            ::= { hwDot3ahEfmEventConfigEntry 11 }


        hwDot3ahEfmErrFrameSecsSummaryWindow OBJECT-TYPE
            SYNTAX Integer32 (100..9000)
            UNITS "tenths of a second"
            MAX-ACCESS read-write
            STATUS current
            DESCRIPTION
                "The amount of time (in 100ms intervals) over which the
                threshold is defined.  The default value is 600 (60 seconds).

                If hwDot3ahEfmErrFrameSecsSummaryThreshold frame errors occur
                within a window of hwDot3ahEfmErrFrameSecsSummaryWindow (in tenths
                of seconds), an Event Notification OAMPDU should be generated
                with an Errored Frame Seconds Summary Event TLV indicating the
                threshold has been crossed in this window.
                "
            REFERENCE
                "[802.3ah], 30.3.6.1.40"
            ::= { hwDot3ahEfmEventConfigEntry 12 }


        hwDot3ahEfmErrFrameSecsSummaryThreshold OBJECT-TYPE
            SYNTAX Integer32 (0..900)
            UNITS "errored frame seconds"
            MAX-ACCESS read-write
            STATUS current
            DESCRIPTION
                "The number of errored frame seconds that must occur for this
                event to be triggered.  The default value is one errored frame
                second. If the threshold value is zero, then an Event
                Notification OAMPDU is sent periodically (at the end of every
                window).  This can be used as an asynchronous notification to
                the peer OAM entity of the statistics related to this
                threshold crossing alarm.

                If hwDot3ahEfmErrFrameSecsSummaryThreshold frame errors occur
                within a window of hwDot3ahEfmErrFrameSecsSummaryWindow (in tenths
                of seconds), an Event Notification OAMPDU should be generated
                with an Errored Frame Seconds Summary Event TLV indicating the
                threshold has been crossed in this window.
                "
            REFERENCE
                "[802.3ah], 30.3.6.1.40"
            ::= { hwDot3ahEfmEventConfigEntry 13 }


        hwDot3ahEfmErrFrameSecsEvNotifEnable OBJECT-TYPE
            SYNTAX TruthValue
            MAX-ACCESS read-write
            STATUS current
            DESCRIPTION
                "If true, the local OAM entity should send an Event
                Notification OAMPDU when an Errored Frame Seconds Event
                occurs.

                By default, this object should have the value true for
                Ethernet like interfaces that support OAM.  If the OAM layer
                does not support event notifications (as indicated via the
                hwDot3ahEfmFunctionsSupported attribute), this value is ignored.
                "
            ::= { hwDot3ahEfmEventConfigEntry 14 }


        hwDot3ahEfmDyingGaspEnable OBJECT-TYPE
            SYNTAX TruthValue
            MAX-ACCESS read-write
            STATUS current
            DESCRIPTION
                "If true, the local OAM entity should attempt to indicate a
                dying gasp via the OAMPDU flags field to its peer OAM entity
                when a dying gasp event occurs.  The exact definition of a
                dying gasp event is implementation dependent.  If the system
                does not support dying gasp capability, setting this object
                has no effect, and reading the object should always result in
                'false'.

                By default, this object should have the value true for
                Ethernet like interfaces that support OAM.  If the OAM layer
                does not support event notifications (as indicated via the
                hwDot3ahEfmFunctionsSupported attribute), this value is ignored.
                "
            ::= { hwDot3ahEfmEventConfigEntry 15 }


        hwDot3ahEfmCriticalEventEnable OBJECT-TYPE
            SYNTAX TruthValue
            MAX-ACCESS read-write
            STATUS current
            DESCRIPTION
                "If true, the local OAM entity should attempt to indicate a
                critical event via the OAMPDU flags to its peer OAM entity
                when a critical event occurs.   The exact definition of a
                critical event is implementation dependent.  If the system
                does not support critical event capability, setting this
                object has no effect, and reading the object should always
                result in 'false'.

                By default, this object should have the value true for
                Ethernet like interfaces that support OAM.  If the OAM layer
                does not support event notifications (as indicated via the
                hwDot3ahEfmFunctionsSupported attribute), this value is ignored.
                "
            ::= { hwDot3ahEfmEventConfigEntry 16 }


        hwDot3ahEfmThresholdTriggerErrDown OBJECT-TYPE
            SYNTAX      EnabledStatus
            MAX-ACCESS  read-write
            STATUS      current
            DESCRIPTION
                "This object indicates whether threshold event will trigger error-shutdown.
                If it is enabled(1), after EFM checks that the threshold event happens,
                the current interface will be set to administrative down.

                The default value is disabled(2).
                "
            ::= { hwDot3ahEfmEventConfigEntry 17 }



--  **************************************************************
--
-- Ethernet OAM Event Log group
--
        hwDot3ahEfmEventLogTable OBJECT-TYPE
            SYNTAX SEQUENCE OF HwDot3ahEfmEventLogEntry
            MAX-ACCESS not-accessible
            STATUS current
            DESCRIPTION
                "This table records a history of the events that have occurred
                at the Ethernet OAM level.  These events can include locally
                detected events, which may result in locally generated
                OAMPDUs, and remotely detected events, which are detected by
                the OAM peer entity and signaled to the local entity via
                Ethernet OAM.  Ethernet OAM events can be signaled by Event
                Notification OAMPDUs or by the flags field in any OAMPDU.

                This table contains both threshold crossing events and
                non-threshold crossing events.  The parameters for the
                threshold window, threshold value, and actual value
                (hwDot3ahEfmEventLogWindowXX, hwDot3ahEfmEventLogThresholdXX,
                hwDot3ahEfmEventLogValue) are only applicable to threshold
                crossing events, and are returned as all F's (2^32 - 1) for
                non-threshold crossing events.
                Entries in the table are automatically created when such
                events are detected.  The size of the table is implementation
                dependent.  When the table reaches its maximum size, older
                entries are automatically deleted to make room for newer
                entries.
                "
            ::= { hwDot3ahEfmObject 7 }


        hwDot3ahEfmEventLogEntry OBJECT-TYPE
            SYNTAX HwDot3ahEfmEventLogEntry
            MAX-ACCESS not-accessible
            STATUS current
            DESCRIPTION
                "An entry in the hwDot3ahEfmEventLogTable.  Entries are
                automatically created whenever Ethernet OAM events occur at
                the local OAM entity, and when Event Notification OAMPDUs are
                received at the local OAM entity (indicating events have
                occurred at the peer OAM entity).  The size of the table is
                implementation dependent, but when the table becomes full,
                older events are automatically deleted to make room for newer
                events.  The table index hwDot3ahEfmEventLogIndex increments for
                each new entry, and when the maximum value is reached the
                value restarts at zero.
                "
            INDEX { ifIndex, hwDot3ahEfmEventLogIndex }
            ::= { hwDot3ahEfmEventLogTable 1 }


        HwDot3ahEfmEventLogEntry ::=
            SEQUENCE {
                hwDot3ahEfmEventLogIndex
                    Unsigned32,
                hwDot3ahEfmEventLogTimestamp
                    TimeStamp,
                hwDot3ahEfmEventLogOui
                    HWDot3Oui,
                hwDot3ahEfmEventLogType
                    Unsigned32,
                hwDot3ahEfmEventLogLocation
                    INTEGER,
                hwDot3ahEfmEventLogWindowHi
                    Unsigned32,
                hwDot3ahEfmEventLogWindowLo
                    Unsigned32,
                hwDot3ahEfmEventLogThresholdHi
                    Unsigned32,
                hwDot3ahEfmEventLogThresholdLo
                    Unsigned32,
                hwDot3ahEfmEventLogValue
                    CounterBasedGauge64,
                hwDot3ahEfmEventLogRunningTotal
                    CounterBasedGauge64,
                hwDot3ahEfmEventLogEventTotal
                    Unsigned32
             }

        hwDot3ahEfmEventLogIndex OBJECT-TYPE
            SYNTAX Unsigned32
            MAX-ACCESS not-accessible
            STATUS current
            DESCRIPTION
                "An arbitrary integer for identifying individual events
                within the event log.  "
            ::= { hwDot3ahEfmEventLogEntry 1 }


        hwDot3ahEfmEventLogTimestamp OBJECT-TYPE
            SYNTAX TimeStamp
            MAX-ACCESS read-only
            STATUS current
            DESCRIPTION
                "The value of sysUpTime at the time of the logged event.  For
                locally generated events, the time of the event can be
                accurately retrieved from sysUpTime.  For remotely generated
                events, the time of the event is indicated by the reception of
                the Event Notification OAMPDU indicating the event occurred on
                the peer.  A system may attempt to adjust the timestamp value
                to more accurately reflect the time of the event at the peer
                OAM entity by using other information, such as that found in
                the timestamp found of the Event Notification TLVs, which
                provides an indication of the relative time between events at
                the peer entity.  "
            ::= { hwDot3ahEfmEventLogEntry 2 }


        hwDot3ahEfmEventLogOui OBJECT-TYPE
            SYNTAX HWDot3Oui
            MAX-ACCESS read-only
            STATUS current
            DESCRIPTION
                "The OUI of the entity defining the object type.  All IEEE
                802.3 defined events (as appearing in [802.3ah] except for the
                Organizationally Unique Event TLVs) use the IEEE 802.3 OUI of
                0x0180C2.  Organizations defining their own Event Notification
                TLVs include their OUI in the Event Notification TLV which
                gets reflected here.  "
            ::= { hwDot3ahEfmEventLogEntry 3 }


        hwDot3ahEfmEventLogType OBJECT-TYPE
            SYNTAX Unsigned32
            MAX-ACCESS read-only
            STATUS current
            DESCRIPTION
                "The type of event that generated this entry in the event log.

                When the OUI is the IEEE 802.3 OUI of 0x0180C2, the following
                event types are defined:
                    erroredSymbolEvent(1),
                    erroredFrameEvent(2),
                    erroredFramePeriodEvent(3),
                    erroredFrameSecondsEvent(4),
                    lostlink(254),
                    linkFault(256),
                    dyingGaspEvent(257),
                    criticalLinkEvent(258)
                The first four are considered threshold crossing events as
                they are generated when a metric exceeds a given value within
                a specified window.  The other three are not threshold
                crossing events.

                When the OUI is not 71874 (0x0180C2 in hex), then some other
                organization has defined the event space.  If event subtyping
                is known to the implementation, it may be reflected here.
                Otherwise, this value should return all Fs (2^32 - 1).
                "
            REFERENCE
                "[802.3ah], 30.3.6.1.10 and 57.5.3."
            ::= { hwDot3ahEfmEventLogEntry 4 }


        hwDot3ahEfmEventLogLocation OBJECT-TYPE
            SYNTAX INTEGER
                {
                local(1),
                remote(2)
                }
            MAX-ACCESS read-only
            STATUS current
            DESCRIPTION
                "Whether this event occurred locally (local(1)), or was
                received from the OAM peer via Ethernet OAM (remote(2)).
                "
            ::= { hwDot3ahEfmEventLogEntry 5 }


        hwDot3ahEfmEventLogWindowHi OBJECT-TYPE
            SYNTAX Unsigned32
            MAX-ACCESS read-only
            STATUS current
            DESCRIPTION
                "If the event represents a threshold crossing event, the two
                objects hwDot3ahEfmEventWindowHi and hwDot3ahEfmEventWindowLo form an
                unsigned 64-bit integer yielding the window over which the
                value was measured for the threshold crossing event (for
                example, 5, when 11 occurrences happened in 5 seconds while
                the threshold was 10).   The two objects are combined as:

                hwDot3ahEfmEventLogWindow = ((2^32) * hwDot3ahEfmEventLogWindowHi)
                                                + hwDot3ahEfmEventLogWindowLo


                Otherwise, this value is returned as all F's (2^32 - 1) and
                adds no useful information.
                "
            REFERENCE
                "[802.3ah], 30.3.6.1.37 and 57.5.3.2."
            ::= { hwDot3ahEfmEventLogEntry 6 }


        hwDot3ahEfmEventLogWindowLo OBJECT-TYPE
            SYNTAX Unsigned32
            MAX-ACCESS read-only
            STATUS current
            DESCRIPTION
                "If the event represents a threshold crossing event, the two
                objects hwDot3ahEfmEventWindowHi and hwDot3ahEfmEventWindowLo form an
                unsigned 64-bit integer yielding the window over which the
                value was measured for the threshold crossing event (for
                example, 5, when 11 occurrences happened in 5 seconds while
                the threshold was 10).   The two objects are combined as:

                hwDot3ahEfmEventLogWindow = ((2^32) * hwDot3ahEfmEventLogWindowHi)
                                                + hwDot3ahEfmEventLogWindowLo

                Otherwise, this value is returned as all F's (2^32 - 1) and
                adds no useful information.
                "
            REFERENCE
                "[802.3ah], 30.3.6.1.37 and 57.5.3.2."
            ::= { hwDot3ahEfmEventLogEntry 7 }


        hwDot3ahEfmEventLogThresholdHi OBJECT-TYPE
            SYNTAX Unsigned32
            MAX-ACCESS read-only
            STATUS current
            DESCRIPTION
                "If the event represents a threshold crossing event, the two
                objects hwDot3ahEfmEventThresholdHi and hwDot3ahEfmEventThresholdLo
                form an unsigned 64-bit integer yielding the value that was
                crossed for the threshold crossing event (for example, 10,
                when 11 occurrences happened in 5 seconds while the threshold
                was 10).  The two objects are combined as:

                hwDot3ahEfmEventLogThreshold = ((2^32) * hwDot3ahEfmEventLogThresholdHi)
                                                 + hwDot3ahEfmEventLogThresholdLo

                Otherwise, this value is returned as all F's (2^32 -1) and
                adds no useful information.
                "
            REFERENCE
                "[802.3ah], 30.3.6.1.37 and 57.5.3.2."
            ::= { hwDot3ahEfmEventLogEntry 8 }


        hwDot3ahEfmEventLogThresholdLo OBJECT-TYPE
            SYNTAX Unsigned32
            MAX-ACCESS read-only
            STATUS current
            DESCRIPTION
                "If the event represents a threshold crossing event, the two
                objects hwDot3ahEfmEventThresholdHi and hwDot3ahEfmEventThresholdLo
                form an unsigned 64-bit integer yielding the value that was
                crossed for the threshold crossing event (for example, 10,
                when 11 occurrences happened in 5 seconds while the threshold
                was 10).  The two objects are combined as:

                hwDot3ahEfmEventLogThreshold = ((2^32) * hwDot3ahEfmEventLogThresholdHi)
                                                 + hwDot3ahEfmEventLogThresholdLo

                Otherwise, this value is returned as all F's (2^32 - 1) and
                adds no useful information.
                "
            REFERENCE
                "[802.3ah], 30.3.6.1.37 and 57.5.3.2."
            ::= { hwDot3ahEfmEventLogEntry 9 }


        hwDot3ahEfmEventLogValue OBJECT-TYPE
            SYNTAX CounterBasedGauge64
            MAX-ACCESS read-only
            STATUS current
            DESCRIPTION
                "If the event represents a threshold crossing event, this
                value indicates the value of the parameter within the given
                window that generated this event (for example, 11, when 11
                occurrences happened in 5 seconds while the threshold was 10).

                Otherwise, this value is returned as all F's
                (2^64 - 1) and adds no useful information.
                "
            REFERENCE
                "[802.3ah], 30.3.6.1.37 and 57.5.3.2."
            ::= { hwDot3ahEfmEventLogEntry 10 }


        hwDot3ahEfmEventLogRunningTotal OBJECT-TYPE
            SYNTAX CounterBasedGauge64
            MAX-ACCESS read-only
            STATUS current
            DESCRIPTION
                "Each Event Notification TLV contains a running total of the
                number of times an event has occurred, as well as the number
                of times an Event Notification for the event has been
                transmitted.  For non-threshold crossing events, the number of
                events (hwDot3ahEfmLogRunningTotal) and the number of resultant
                Event Notifications (hwDot3ahEfmLogEventTotal) should be
                identical.

                For threshold crossing events, since multiple occurrences may
                be required to cross the threshold, these values are likely
                different.  This value represents the total number of times
                this event has happened since the last reset (for example,
                3253, when 3253 symbol errors have occurred since the last
                reset, which has resulted in 51 symbol error threshold
                crossing events since the last reset).
                "
            REFERENCE
                "[802.3ah], 30.3.6.1.37 and 57.5.3.2."
            ::= { hwDot3ahEfmEventLogEntry 11 }


        hwDot3ahEfmEventLogEventTotal OBJECT-TYPE
            SYNTAX Unsigned32
            MAX-ACCESS read-only
            STATUS current
            DESCRIPTION
                "Each Event Notification TLV contains a running total of the
                number of times an event has occurred, as well as the number
                of times an Event Notification for the event has been
                transmitted.  For non-threshold crossing events, the number of
                events (hwDot3ahEfmLogRunningTotal) and the number of resultant
                Event Notifications (hwDot3ahEfmLogEventTotal) should be
                identical.

                For threshold crossing events, since multiple occurrences may
                be required to cross the threshold, these values are likely
                different.  This value represents the total number of times
                one or more of these occurrences have resulted in an Event
                Notification (for example, 51 when 3253 symbol errors have
                occurred since the last reset, which has resulted in 51 symbol
                error threshold crossing events since the last reset).
                "
            REFERENCE
                "[802.3ah], 30.3.6.1.37 and 57.5.3.2."
            ::= { hwDot3ahEfmEventLogEntry 12 }

        hwDot3ahEfmManagerTable OBJECT-TYPE
            SYNTAX SEQUENCE OF HwDot3ahEfmManagerEntry
            MAX-ACCESS not-accessible
            STATUS current
            DESCRIPTION
                "This table contains configurations of binding relationships
                 between EFM and other modules.
                "
            ::= { hwDot3ahEfmObject 8 }


        hwDot3ahEfmManagerEntry OBJECT-TYPE
            SYNTAX HwDot3ahEfmManagerEntry
            MAX-ACCESS not-accessible
            STATUS current
            DESCRIPTION
                "This entry contains configurations of binding relationships
                 between EFM and other modules.
                "
            INDEX { ifIndex }
            ::= { hwDot3ahEfmManagerTable 1 }


        HwDot3ahEfmManagerEntry ::=
            SEQUENCE {
                hwDot3ahEfmTriggerIfDown
                    EnabledStatus,
                hwDot3ahEfmHoldUpTime
                    Integer32

             }

        hwDot3ahEfmTriggerIfDown OBJECT-TYPE
            SYNTAX EnabledStatus
            MAX-ACCESS read-write
            STATUS current
            DESCRIPTION
                "This object indicates whether EFM is bound to the interface.
                If it is enabled(1), after EFM checks that the link times out,
                the current Ethernet interface link state will be set to block (EFM
                down),and all the data except the OAMPDU is blocked.

                The default value is disabled(2).
                "
            ::= { hwDot3ahEfmManagerEntry 1 }
            
            
        hwDot3ahEfmHoldUpTime OBJECT-TYPE
            SYNTAX Integer32 (0..50)
            MAX-ACCESS read-write
            STATUS current
            DESCRIPTION
                "This object specifies the time elapsed an EFM interface is
                in the faulty state. The value ranges from 0 to 50 in seconds.
                
                The default value is 0.
                "
            ::= { hwDot3ahEfmManagerEntry 2 }

-- Ethernet OAM EVRRP group
-- add by liujin 64168 2008-9-25

      hwDot3ahEvrrpTable OBJECT-TYPE
        SYNTAX      SEQUENCE OF HwDot3ahEvrrpEntry
        MAX-ACCESS  not-accessible
        STATUS      current
        DESCRIPTION
          "This table contains information about the OAM Evrrp project for
          a particular Ethernet like interface.
          "
        ::= { hwDot3ahEfmObject 9 }

      hwDot3ahEvrrpEntry OBJECT-TYPE
        SYNTAX      HwDot3ahEvrrpEntry
        MAX-ACCESS  not-accessible
        STATUS      current
        DESCRIPTION
          "An entry in the table of hwDot3ahEvrrpTable, containing information on
          the OAM Evrrp entity for a single Ethernet like interface.

          Note that there is at most one OAM Evrrp for each Ethernet like
          interface.
          "
        INDEX       { ifIndex }
        ::= { hwDot3ahEvrrpTable 1 }


      HwDot3ahEvrrpEntry ::=
        SEQUENCE {
          hwDot3ahEvrrpCpuState                INTEGER,
          hwDot3ahEvrrpTriggerIfDown           EnabledStatus,
          hwDot3ahEvrrpHoldUpTime              Integer32
        }

      hwDot3ahEvrrpCpuState OBJECT-TYPE
        SYNTAX      INTEGER {
                      master(1),
                      slave(2),
                      unknown(3)
                    }
        MAX-ACCESS  read-only
        STATUS      current
        DESCRIPTION
          "This object indicates the state in the OAMPDU which sended by
          the peer interface.

          If it is master(1), EFM will make the link work as the master
          state. And if it is slave(2), EFM will make the link works as
          the slave chain link.

          The default state is unknown(3). That means the peer interface
          didn't send any OAMPDU which contains the state of link status.
          "
        ::= { hwDot3ahEvrrpEntry 1 }

      hwDot3ahEvrrpTriggerIfDown OBJECT-TYPE
        SYNTAX      EnabledStatus
        MAX-ACCESS  read-write
        STATUS      obsolete
        DESCRIPTION
          "This object indicates whether EFM is bound to the interface.
          If it is enabled(1), after EFM checks that the link times out,
          the current Ethernet interface link state will be set to EFM
          down. And all of the PDU operation will be stop.

          The default value is disabled(2).
          "
        ::= { hwDot3ahEvrrpEntry 2 }

      hwDot3ahEvrrpHoldUpTime OBJECT-TYPE
        SYNTAX      Integer32 (0..50)
        MAX-ACCESS  read-write
        STATUS      obsolete
        DESCRIPTION
          "This object specifies the time elapsed an EFM interface is
           in the faulty state. The value ranges from 0 to 50 in seconds.

          The default value is 0.
          "
        ::= { hwDot3ahEvrrpEntry 3 }


--  
--  END for EVRRP
--  

        hwOamManager OBJECT IDENTIFIER ::= { hwEthOamMib 3 }


        hwTestMessage OBJECT IDENTIFIER ::= { hwEthOamMib 4 }


        hwTestMessageObject OBJECT IDENTIFIER ::= { hwTestMessage 1 }


--  hwTestMessageTableNextIndex
        hwTestMessageTableNextIndex OBJECT-TYPE
            SYNTAX Unsigned32
            MAX-ACCESS read-only
            STATUS current
            DESCRIPTION
                "
                Search the next hwTestMessageTable instance.
                "
            ::= { hwTestMessageObject 1 }


--  hwDot3ahEfmDetectModeTable
        hwTestMessageTable OBJECT-TYPE
            SYNTAX SEQUENCE OF HwTestMessageEntry
            MAX-ACCESS not-accessible
            STATUS current
            DESCRIPTION
                "
                The definition of the tested packets format and the transmission of the tested packets
                "
            ::= { hwTestMessageObject 2 }


        hwTestMessageEntry OBJECT-TYPE
            SYNTAX HwTestMessageEntry
            MAX-ACCESS not-accessible
            STATUS current
            DESCRIPTION
                "Entry for Test Message Table."
            INDEX { hwTestMessageIndex }
            ::= { hwTestMessageTable 1 }


        HwTestMessageEntry ::=
            SEQUENCE {
                hwTestMessageIndex
                    Unsigned32,
                hwTestMessageMacAddress
                    MacAddress,
                hwTestMessageVlanID
                    Unsigned32,
                hwTestMessageInterface
                    OCTET STRING,
                hwTestMessageServiceInstance
                    OCTET STRING,
                hwTestMessagePacketSize
                    Unsigned32,
                hwTestMessageSendPackets
                    Unsigned32,
                hwTestMessageSendSpeed
                    HWTestMessageSendSpeed,
                hwTestMessageSendEnabled
                    TruthValue,
                hwTestMessageSendFinished
                    HWTestMessageFinishedValue,
                hwTestMessageRowStatus
                    RowStatus
             }

        hwTestMessageIndex OBJECT-TYPE
            SYNTAX Unsigned32
            MAX-ACCESS not-accessible
            STATUS current
            DESCRIPTION
                "
                Set the index for the tested packets table
                "
            ::= { hwTestMessageEntry 1 }


        hwTestMessageMacAddress OBJECT-TYPE
            SYNTAX MacAddress
            MAX-ACCESS read-create
            STATUS current
            DESCRIPTION
                "
                The destination MAC address

                "
            ::= { hwTestMessageEntry 11 }


        hwTestMessageVlanID OBJECT-TYPE
            SYNTAX Unsigned32
            MAX-ACCESS read-create
            STATUS current
            DESCRIPTION
                "
                VLAN index
                "
            ::= { hwTestMessageEntry 12 }


        hwTestMessageInterface OBJECT-TYPE
            SYNTAX OCTET STRING
            MAX-ACCESS read-create
            STATUS current
            DESCRIPTION
                "
                If the interface is specified, specify the interface name.
                "
            ::= { hwTestMessageEntry 13 }


        hwTestMessageServiceInstance OBJECT-TYPE
            SYNTAX OCTET STRING
            MAX-ACCESS read-create
            STATUS current
            DESCRIPTION
                "
                Name of the service instance
                "
            ::= { hwTestMessageEntry 14 }


        hwTestMessagePacketSize OBJECT-TYPE
            SYNTAX Unsigned32 (64..1518)
            MAX-ACCESS read-create
            STATUS current
            DESCRIPTION
                "
                The length of the sent tested packets ranges from 64 to 1518 in byte, and the default value is 64.
                "
            DEFVAL { 64 }
            ::= { hwTestMessageEntry 15 }


        hwTestMessageSendPackets OBJECT-TYPE
            SYNTAX Unsigned32 (1..65535)
            MAX-ACCESS read-create
            STATUS current
            DESCRIPTION
                "
                The number of the sent tested packets ranges from 1 to 65535 in integer, and the default value is 5.
                "
            DEFVAL { 5 }
            ::= { hwTestMessageEntry 16 }


        hwTestMessageSendSpeed OBJECT-TYPE
            SYNTAX HWTestMessageSendSpeed
            MAX-ACCESS read-create
            STATUS current
            DESCRIPTION
                "
                Enumerated type indicates the rate of sending the packets: oneMbps and fiveMbps. The default is oneMbps.
                "
            DEFVAL { oneMbps }
            ::= { hwTestMessageEntry 17 }


        hwTestMessageSendEnabled OBJECT-TYPE
            SYNTAX TruthValue
            MAX-ACCESS read-create
            STATUS current
            DESCRIPTION
                "
                The sending and termination of the tested packets
                "
            ::= { hwTestMessageEntry 18 }


        hwTestMessageSendFinished OBJECT-TYPE
            SYNTAX HWTestMessageFinishedValue
            MAX-ACCESS read-only
            STATUS current
            DESCRIPTION
                "
                View whether the tested packets are stopped to be sent:
                1, 2, 3, 4, and 5 indicate that has not run/is running/the previous test terminates normally/the previous test terminates abnormally/the previous test is interrupted (through ctrl+c or mib)
                "
            ::= { hwTestMessageEntry 19 }


        hwTestMessageRowStatus OBJECT-TYPE
            SYNTAX RowStatus
            MAX-ACCESS read-create
            STATUS current
            DESCRIPTION
                "
                The status of the row.

                The writable columns in a row can not be changed if the row
                is active. All columns must have a valid value before a row
                can be activated.
                "
            ::= { hwTestMessageEntry 51 }


        hwTestMessageResultTable OBJECT-TYPE
            SYNTAX SEQUENCE OF HwTestMessageResultEntry
            MAX-ACCESS not-accessible
            STATUS current
            DESCRIPTION
                "
                View the returned results after tests
                "
            ::= { hwTestMessageObject 3 }


        hwTestMessageResultEntry OBJECT-TYPE
            SYNTAX HwTestMessageResultEntry
            MAX-ACCESS not-accessible
            STATUS current
            DESCRIPTION
                "Entry for Test Message Table."
            INDEX { hwTestMessageIndex }
            ::= { hwTestMessageResultTable 1 }


        HwTestMessageResultEntry ::=
            SEQUENCE {
                hwTestMessageResultSendPackets
                    Unsigned32,
                hwTestMessageResultReceivedPackets
                    Unsigned32,
                hwTestMessageResultPacketsLost
                    Unsigned32,
                hwTestMessageResultSendBytes
                    Unsigned32,
                hwTestMessageResultReceivedBytes
                    Unsigned32,
                hwTestMessageResultBytesLost
                    Unsigned32,
                hwTestMessageBeginTimeStamp
                    TimeStamp,
                hwTestMessageEndTimeStamp
                    TimeStamp
             }

        hwTestMessageResultSendPackets OBJECT-TYPE
            SYNTAX Unsigned32
            MAX-ACCESS read-only
            STATUS current
            DESCRIPTION
                "
                The number of the sent packets
                "
            ::= { hwTestMessageResultEntry 11 }


        hwTestMessageResultReceivedPackets OBJECT-TYPE
            SYNTAX Unsigned32
            MAX-ACCESS read-only
            STATUS current
            DESCRIPTION
                "
                The number of the received packets
                "
            ::= { hwTestMessageResultEntry 12 }


        hwTestMessageResultPacketsLost OBJECT-TYPE
            SYNTAX Unsigned32
            MAX-ACCESS read-only
            STATUS current
            DESCRIPTION
                "
                Packets loss ratio
                "
            ::= { hwTestMessageResultEntry 13 }


        hwTestMessageResultSendBytes OBJECT-TYPE
            SYNTAX Unsigned32
            MAX-ACCESS read-only
            STATUS current
            DESCRIPTION
                "
                The number of the sent bytes
                "
            ::= { hwTestMessageResultEntry 14 }


        hwTestMessageResultReceivedBytes OBJECT-TYPE
            SYNTAX Unsigned32
            MAX-ACCESS read-only
            STATUS current
            DESCRIPTION
                "
                The number of the received bytes
                "
            ::= { hwTestMessageResultEntry 15 }


        hwTestMessageResultBytesLost OBJECT-TYPE
            SYNTAX Unsigned32
            MAX-ACCESS read-only
            STATUS current
            DESCRIPTION
                "
                The number of the lost bytes
                "
            ::= { hwTestMessageResultEntry 16 }


        hwTestMessageBeginTimeStamp OBJECT-TYPE
            SYNTAX TimeStamp
            MAX-ACCESS read-only
            STATUS current
            DESCRIPTION
                "
                The time of starting the Test operation
                "
            ::= { hwTestMessageResultEntry 17 }


        hwTestMessageEndTimeStamp OBJECT-TYPE
            SYNTAX TimeStamp
            MAX-ACCESS read-only
            STATUS current
            DESCRIPTION
                "
                The time of ending the Test operation
                "
            ::= { hwTestMessageResultEntry 18 }


        hwEthOamTraps OBJECT IDENTIFIER ::= { hwEthOamMib 6 }


--  ******************************************************************
-- NOTIFICATIONS (TRAPS)
-- These notifications will be sent to the management entity
-- whenever a MEP loses/restores contact with one or more other MEPs.
-- ******************************************************************
        hwDot1agCfmFaultAlarm NOTIFICATION-TYPE
            OBJECTS { hwDot1agCfmRMepMacAddress, hwDot1agCfmRMepHighestPrDefect, hwDot1agCfmMdName, hwDot1agCfmMdMdLevel, hwDot1agCfmMaName
                 }
            STATUS current
            DESCRIPTION
                "A MEP has lost contact with one or more MEPs. A notification
                (fault alarm) is sent to the management entity with the OID
                of the MEP that has detected the fault.

                Whenever a MEP loses contact with one or more other MEPs,
                it may or may not generate a Fault Alarm to warn the system
                administrator of the problem, as controlled by the MEP
                Fault Notification Generator State Machine and associated
                Managed Objects. Only the highest-priority defect, as shown
                in Table 20-1, is reported in the Fault Alarm.
                          hwDot1agCfmRMepMacAddress   The MAC address of the remote faulty MEP
                          hwDot1agCfmRMepHighestPrDefect   The fault in the highest level
                          hwDot1agCfmMdName                The name of the faulty MD
                          hwDot1agCfmMdLevel               The level of the faulty MD
                          hwDot1agCfmMaName                The name of the faulty MA
                             "
            REFERENCE
                "802.1ag clause 12.14.7.7"
            ::= { hwEthOamTraps 1 }


        hwTestMessageFailed NOTIFICATION-TYPE
            OBJECTS { hwTestMessageSendFinished }
            STATUS obsolete
            DESCRIPTION
                "
                The events after tests are reported.
                1,2,3,4, and 5 indicate has not run/is running/the previous test terminates normally/the previous test terminate abnormally/the previous test is interrupted.
                (through ctrl+c or mib)
                "
            REFERENCE
                " "
            ::= { hwEthOamTraps 2 }


        hwTestMessageCompleted NOTIFICATION-TYPE
            OBJECTS { hwTestMessageSendFinished, hwTestMessageResultSendPackets, hwTestMessageResultReceivedPackets, hwTestMessageResultPacketsLost, hwTestMessageResultSendBytes,
                hwTestMessageResultReceivedBytes, hwTestMessageResultBytesLost, hwTestMessageBeginTimeStamp, hwTestMessageEndTimeStamp }
            STATUS obsolete
            DESCRIPTION
                "
                After the test is complete, report the results to the network management.
                "
            REFERENCE
                " "
            ::= { hwEthOamTraps 3 }


--  ***************************************************************
--
-- Ethernet OAM Notifications
--
        hwDot3ahEfmThresholdEvent NOTIFICATION-TYPE
            OBJECTS { hwDot3ahEfmEventLogTimestamp, hwDot3ahEfmEventLogOui, hwDot3ahEfmEventLogType, hwDot3ahEfmEventLogLocation, hwDot3ahEfmEventLogWindowHi,
                hwDot3ahEfmEventLogWindowLo, hwDot3ahEfmEventLogThresholdHi, hwDot3ahEfmEventLogThresholdLo, hwDot3ahEfmEventLogValue, hwDot3ahEfmEventLogRunningTotal,
                hwDot3ahEfmEventLogEventTotal }
            STATUS current
            DESCRIPTION
                "A hwDot3ahEfmThresholdEvent notification is sent when a local or
                remote threshold crossing event is detected.  A local
                threshold crossing event is detected by the local entity,
                while a remote threshold crossing event is detected by the
                reception of an Ethernet OAM Event Notification OAMPDU
                indicating a threshold event.

                This notification should not be sent more than once per
                second.

                The OAM entity can be derived from extracting the ifIndex from
                the variable bindings.  The objects in the notification
                correspond to the values in a row instance of in the
                hwDot3ahEfmEventLogTable.

                The management entity should periodically check
                hwDot3ahEfmEventLogTable to detect any missed events."
            ::= { hwEthOamTraps 4 }


        hwDot3ahEfmNonThresholdEvent NOTIFICATION-TYPE
            OBJECTS { hwDot3ahEfmEventLogTimestamp, hwDot3ahEfmEventLogOui, hwDot3ahEfmEventLogType, hwDot3ahEfmEventLogLocation}

            STATUS current
            DESCRIPTION
                "A hwDot3ahEfmNonThresholdEvent notification is sent when a local
                or remote non-threshold crossing event is detected.  A local
                event is detected by the local entity, while a remote event is
                detected by the reception of an Ethernet OAM Event
                Notification OAMPDU indicating a non-threshold crossing event.

                This notification should not be sent more than once per
                second.

                The OAM entity can be derived from extracting the ifIndex from
                the variable bindings.  The objects in the notification
                correspond to the values in a row instance of the
                hwDot3ahEfmEventLogTable.

                The management entity should periodically check
                hwDot3ahEfmEventLogTable to detect any missed events."
            ::= { hwEthOamTraps 5 }

        hwDot3ahEfmRemoteDyingGaspEvent NOTIFICATION-TYPE
            OBJECTS { hwDot3ahEfmPeerMacAddress, ifDescr
                 }
            STATUS current
            DESCRIPTION
                "A hwDot3ahEfmRemoteDyingGaspEvent notification is sent when a remote
                Dying-Gasp event is detected. A remote event is detected by
                the reception of an Ethernet OAM Event Notification OAMPDU
                indicating a Dying-Gasp event."
            ::= { hwEthOamTraps 8 }

        hwDot3ahEfmNonThresholdRecovery  NOTIFICATION-TYPE
            OBJECTS { hwDot3ahEfmEventLogTimestamp, hwDot3ahEfmEventLogOui, hwDot3ahEfmEventLogType, hwDot3ahEfmEventLogLocation}
            STATUS current
            DESCRIPTION
                "A hwDot3ahEfmNonThresholdRecovery notification is sent when a hwDot3ahEfmNonThresholdEvent is recovered."
            ::= { hwEthOamTraps 17 }

        hwCfmVlanOnewayDelay NOTIFICATION-TYPE
            OBJECTS { hwCfmOneDelayTrapLogMacAddress,
              hwCfmVlanOneDelayTrapLogTimestamp, hwCfmVlanOneDelayTrapLogDelayValue, 
              hwCfmVlanOneDelayTrapLogThreshold, hwCfmVlanOneDelayTrapLogDelayValueHigh, hwCfmVlanOneDelayTrapLogDelayValueLow }
            STATUS current
            DESCRIPTION
                "
                In the VLAN networking, the oneway delay exceeded the trap threshold.
                "
            ::= { hwEthOamTraps 23 }

        hwCfmVlanOnewayDelayRecovery NOTIFICATION-TYPE
            OBJECTS { hwCfmOneDelayRecoveryTrapMacAddress,
              hwCfmVlanOneDelayRecoveryTrapLogTimestamp, hwCfmVlanOneDelayRecoveryTrapLogDelayValue,
              hwCfmVlanOneDelayRecoveryTrapLogThreshold, hwCfmVlanOneDelayRecoveryTrapLogDelayValueHigh, hwCfmVlanOneDelayRecoveryTrapLogDelayValueLow }
            STATUS current
            DESCRIPTION
                "
                In the VLAN networking, the oneway delay fell below the trap threshold.
                "
            ::= { hwEthOamTraps 24 }

        hwCfmVlanTwowayDelay NOTIFICATION-TYPE
            OBJECTS { hwCfmTwoDelayTrapMacAddress, hwCfmVlanTwoDelayTrapLogTimestamp,
              hwCfmVlanTwoDelayTrapLogDelayValue, hwCfmVlanTwoDelayTrapLogThreshold, hwCfmVlanTwoDelayTrapLogDelayValueHigh, hwCfmVlanTwoDelayTrapLogDelayValueLow }
            STATUS current
            DESCRIPTION
                "
                In the VLAN networking, the twoway delay exceeded the trap threshold.
                "
            ::= { hwEthOamTraps 25 }

        hwCfmVlanTwowayDelayRecovery NOTIFICATION-TYPE
            OBJECTS { hwCfmTwoDelayRecoveryTrapMacAddress,
              hwCfmVlanTwoDelayRecoveryTrapLogTimestamp,
              hwCfmVlanTwoDelayRecoveryTrapLogDelayValue,
              hwCfmVlanTwoDelayRecoveryTrapLogThreshold,
              hwCfmVlanTwoDelayRecoveryTrapLogDelayValueHigh,
              hwCfmVlanTwoDelayRecoveryTrapLogDelayValueLow }
            STATUS current
            DESCRIPTION
                "
                In the VLAN networking, the twoway delay fell below the trap threshold.
                "
            ::= { hwEthOamTraps 26 }

        hwDot3ahEfmLoopbackFailed NOTIFICATION-TYPE
            OBJECTS { ifDescr }
            STATUS current
            DESCRIPTION
                "
                A hwDot3ahEfmLoopbackFailed notification is sent when failed to start
                loopback on a interface.

                This notification should not be sent more than once per
                second.
                "
            ::= { hwEthOamTraps 29 }

        hwY1731AisDefectAlarm NOTIFICATION-TYPE
            OBJECTS { hwDot1agCfmMdName, hwDot1agCfmMaName, hwDot1agCfmMepIdentifier}
            STATUS current
            DESCRIPTION
                "AIS status has been entered."
            ::= { hwEthOamTraps 30 }

        hwY1731AisDefectAlarmRecovery NOTIFICATION-TYPE
            OBJECTS { hwDot1agCfmMdName, hwDot1agCfmMaName, hwDot1agCfmMepIdentifier}
            STATUS current
            DESCRIPTION
                "AIS status has been existed."
            ::= { hwEthOamTraps 31 }

        hwDot1agCfmUnexpectedMEGLevel NOTIFICATION-TYPE
            OBJECTS { hwDot1agCfmMdName, hwDot1agCfmMaName, hwDot1agCfmMepIdentifier }
            STATUS current
            DESCRIPTION
                "Indicates a CCM frame with unexpected MEG level."
            ::= { hwEthOamTraps 32}
            
        hwDot1agCfmUnexpectedMEGLevelCleared NOTIFICATION-TYPE
            OBJECTS { hwDot1agCfmMdName, hwDot1agCfmMaName, hwDot1agCfmMepIdentifier }
            STATUS current
            DESCRIPTION
                "Indicates resuming from receiving a CCM frame with unexpected MEG level."
            ::= { hwEthOamTraps 33}
            
        hwDot1agCfmMismerge NOTIFICATION-TYPE
            OBJECTS { hwDot1agCfmMdName, hwDot1agCfmMaName, hwDot1agCfmMepIdentifier }
            STATUS current
            DESCRIPTION
                "Indicates a CCM frame with unexpected MEG ID"
            ::= { hwEthOamTraps 34 }
        
        hwDot1agCfmMismergeCleared NOTIFICATION-TYPE
            OBJECTS { hwDot1agCfmMdName, hwDot1agCfmMaName, hwDot1agCfmMepIdentifier }
            STATUS current
            DESCRIPTION
                "Indicates resuming from receiving a CCM frame with unexpected MEG ID."
            ::= { hwEthOamTraps 35 }
            
        hwDot1agCfmUnexpectedMEP NOTIFICATION-TYPE
            OBJECTS { hwDot1agCfmMdName, hwDot1agCfmMaName, hwDot1agCfmMepIdentifier }
            STATUS current
            DESCRIPTION
                "Indicates a CCM frame with unexpected MEP ID."
            ::= { hwEthOamTraps 36 }
            
        hwDot1agCfmUnexpectedMEPCleared NOTIFICATION-TYPE
            OBJECTS { hwDot1agCfmMdName, hwDot1agCfmMaName, hwDot1agCfmMepIdentifier }
            STATUS current
            DESCRIPTION
                "Indicates resuming from receiving a CCM frame with unexpected MEP ID."
            ::= { hwEthOamTraps 37 }
            
        hwDot1agCfmUnexpectedPeriod NOTIFICATION-TYPE
            OBJECTS { hwDot1agCfmMdName, hwDot1agCfmMaName, hwDot1agCfmMepIdentifier, hwDot1agCfmRMepIdentifier }
            STATUS current
            DESCRIPTION
                "Indicates a CCM frame with unexpected period."
            ::= { hwEthOamTraps 38}
            
        hwDot1agCfmUnexpectedPeriodCleared NOTIFICATION-TYPE
            OBJECTS { hwDot1agCfmMdName, hwDot1agCfmMaName, hwDot1agCfmMepIdentifier, hwDot1agCfmRMepIdentifier }
            STATUS current
            DESCRIPTION
                "Indicates resuming from receiving a CCM frame with unexpected period."
            ::= { hwEthOamTraps 39 }
            
        hwDot1agCfmUnexpectedMAC NOTIFICATION-TYPE
            OBJECTS { hwDot1agCfmMdName, hwDot1agCfmMaName, hwDot1agCfmMepIdentifier, hwDot1agCfmRMepIdentifier }
            STATUS current
            DESCRIPTION
                "Indicates a CCM frame with unexpected MAC."
            ::= { hwEthOamTraps 40 }
            
        hwDot1agCfmUnexpectedMACCleared NOTIFICATION-TYPE
            OBJECTS { hwDot1agCfmMdName, hwDot1agCfmMaName, hwDot1agCfmMepIdentifier, hwDot1agCfmRMepIdentifier }
            STATUS current
            DESCRIPTION
                "Indicates a CCM frame with unexpected MAC."
            ::= { hwEthOamTraps 41 }
            
        hwDot1agCfmLOC NOTIFICATION-TYPE
            OBJECTS { hwDot1agCfmMdName, hwDot1agCfmMaName, hwDot1agCfmMepIdentifier, hwDot1agCfmRMepIdentifier }
            STATUS current
            DESCRIPTION
                "Indicates that the session losses of continuity."
            ::= { hwEthOamTraps 42 }
            
        hwDot1agCfmLOCCleared NOTIFICATION-TYPE
            OBJECTS { hwDot1agCfmMdName, hwDot1agCfmMaName, hwDot1agCfmMepIdentifier, hwDot1agCfmRMepIdentifier }
            STATUS current
            DESCRIPTION
                "Indicates that the session resumes from lossing of continuity."
            ::= { hwEthOamTraps 43 }

        hwDot1agCfmExceptionalMACStatus NOTIFICATION-TYPE
            OBJECTS { hwDot1agCfmMdName, hwDot1agCfmMaName, hwDot1agCfmMepIdentifier, hwDot1agCfmRMepIdentifier }
            STATUS current
            DESCRIPTION
                "Indicates the remote MEP is reporting an error status in its Port Status TLV or Interface Status TLV."
            ::= { hwEthOamTraps 44 }
            
        hwDot1agCfmExceptionalMACStatusCleared NOTIFICATION-TYPE
            OBJECTS { hwDot1agCfmMdName, hwDot1agCfmMaName, hwDot1agCfmMepIdentifier, hwDot1agCfmRMepIdentifier }
            STATUS current
            DESCRIPTION
                "Indicates the remote MEP resumes from an error status indicated in its Port Status TLV or Interface Status TLV."
            ::= { hwEthOamTraps 45 }

            
        hwDot1agCfmRDI NOTIFICATION-TYPE
            OBJECTS { hwDot1agCfmMdName, hwDot1agCfmMaName, hwDot1agCfmMepIdentifier, hwDot1agCfmRMepIdentifier }
            STATUS current
            DESCRIPTION
                "Indicates that MEP receives a CCM frame with the RDI field set."
            ::= { hwEthOamTraps 46 }
            
        hwDot1agCfmRDICleared NOTIFICATION-TYPE
            OBJECTS { hwDot1agCfmMdName, hwDot1agCfmMaName, hwDot1agCfmMepIdentifier, hwDot1agCfmRMepIdentifier }
            STATUS current
            DESCRIPTION
                "Indicates that MEP receives a CCM frame with the RDI field cleared."
            ::= { hwEthOamTraps 47 }

        hwY1731AisExceedMaxPktNum NOTIFICATION-TYPE
            OBJECTS { hwY1731AisMaxPktNum }
            STATUS current
            DESCRIPTION
                "Indicates that the number of AIS packets transmitted in one second exceeds the upper limit."
            ::= { hwEthOamTraps 48 }

        hwY1731AisExceedMaxPktNumCleared NOTIFICATION-TYPE
            STATUS current
            DESCRIPTION
                "Indicates that the number of AIS packets transmitted in one second under the upper limit."
            ::= { hwEthOamTraps 49 }

        hwY1731LckDefect NOTIFICATION-TYPE
            OBJECTS { hwDot1agCfmMdName, hwDot1agCfmMaName, hwDot1agCfmMepIdentifier}
            STATUS current
            DESCRIPTION
                "LCK status has been entered."
            ::= { hwEthOamTraps 50 }

        hwY1731LckDefectCleared NOTIFICATION-TYPE
            OBJECTS { hwDot1agCfmMdName, hwDot1agCfmMaName, hwDot1agCfmMepIdentifier}
            STATUS current
            DESCRIPTION
                "LCK status has been exited."
            ::= { hwEthOamTraps 51 }
            
        hwY1731Statistic NOTIFICATION-TYPE
            OBJECTS { hwDot1agCfmMdName, hwDot1agCfmMaName, hwDot1agCfmMepIdentifier, hwY1731StatisticTrapLogValue, hwY1731StatisticTrapLogUpperLimitThreshold, hwY1731StatisticTrapLogLowerLimitThreshold, hwY1731StatisticTrapLogValueHigh, hwY1731StatisticTrapLogValueLow}
            STATUS current
            DESCRIPTION
                "The Y.1731 statistic value exceeded the upper limit value of the threshold."
            ::= { hwEthOamTraps 52 }
            
        hwY1731StatisticClear NOTIFICATION-TYPE
            OBJECTS { hwDot1agCfmMdName, hwDot1agCfmMaName, hwDot1agCfmMepIdentifier, hwY1731StatisticTrapLogValue, hwY1731StatisticTrapLogUpperLimitThreshold, hwY1731StatisticTrapLogLowerLimitThreshold, hwY1731StatisticTrapLogValueHigh, hwY1731StatisticTrapLogValueLow}
            STATUS current
            DESCRIPTION
                "The Y.1731 statistic value fell below lower limit value of the threshold."
            ::= { hwEthOamTraps 53 }
			
        hwY1731LckExceedThreshold NOTIFICATION-TYPE
	    OBJECTS { hwY1731LckMaxPktNum, hwY1731LckCurrentPktNum, hwY1731LckUpperThreshold, hwY1731LckLowerThreshold }
            STATUS current
            DESCRIPTION
                "Indicates that the number of LCK packets transmitted in 1 second exceeds the upper limit."
            ::= { hwEthOamTraps 54 }

        hwY1731LckExceedThresholdRecovery NOTIFICATION-TYPE
            OBJECTS { hwY1731LckMaxPktNum, hwY1731LckCurrentPktNum, hwY1731LckUpperThreshold, hwY1731LckLowerThreshold }
	    STATUS current
            DESCRIPTION
                "Indicates that the number of LCK packets transmitted in 1 second falls below the lower limit."
            ::= { hwEthOamTraps 55 }

        hwEthOamConformance OBJECT IDENTIFIER ::= { hwEthOamMib 7 }

        hwEthOamCompliances OBJECT IDENTIFIER ::= { hwEthOamConformance 1 }


        hwEthOamCompliance MODULE-COMPLIANCE
            STATUS current
            DESCRIPTION
                "The compliance statement for the HUAWEI-ETHOAM-MIB"
            MODULE -- this module
                MANDATORY-GROUPS { hwDot1agCfmMdGroup, hwDot1agCfmMaGroup, hwDot1agCfmMepGroup, hwDot1agCfmRMepGroup, hwDot1agCfmMipGroup,
                    hwDot1agCfmMacPingGroup, hwDot1agCfmMacTraceGroup, hwDot1agCfmMacTraceReplyGroup, hwDot3ahEfmDetectModeGroup, hwTestMessageGroup,
                    hwTestMessageResultGroup, hwEthOamTrapsGroup, hwDot1agCfmGroup, hwDot3ahEfmControlGroup, hwDot3ahEfmPeerGroup,
                    hwDot3ahEfmStatsBaseGroup, hwDot3ahEfmManagerGroup}
                OBJECT hwDot1agCfmRMepRowStatus
                    DESCRIPTION
                        "Support for createAndWait is not required."
                OBJECT hwTestMessageRowStatus
                    DESCRIPTION
                        "Support for createAndWait is not required."
                GROUP hwDot3ahEfmLoopbackGroup
                    DESCRIPTION
                        "This group is mandatory for all IEEE 802.3 OAM
                        implementations that support loopback functionality. "
                GROUP hwDot3ahEfmErrSymbolPeriodEventGroup
                    DESCRIPTION
                        "This group is mandatory for all IEEE 802.3 OAM
                        implementations that support event functionality. "
                GROUP hwDot3ahEfmErrFramePeriodEventGroup
                    DESCRIPTION
                        "This group is mandatory for all IEEE 802.3 OAM
                        implementations that support event functionality. "
                GROUP hwDot3ahEfmErrFrameEventGroup
                    DESCRIPTION
                        "This group is mandatory for all IEEE 802.3 OAM
                        implementations that support event functionality. "
                GROUP hwDot3ahEfmErrFrameSecsSummaryEventGroup
                    DESCRIPTION
                        "This group is mandatory for all IEEE 802.3 OAM
                        implementations that support event functionality. "
                GROUP hwDot3ahEfmFlagEventGroup
                    DESCRIPTION
                        "This group is optional for all IEEE 802.3 OAM
                        implementations.  The ability to send critical events or dying
                        gasp events is not required in any system."
                GROUP hwDot3ahEfmEventLogGroup
                    DESCRIPTION
                        "This group is optional for all IEEE 802.3 OAM
                        implementations. Entries in this table are dependent on what
                        event functionality is supported in the local OAM
                        implementation.  At least one type of event must be supported
                        for entries to appear in this table.  "
                GROUP hwY1731ManagerGroup
                    DESCRIPTION
                        "This group is mandatory for all ITU Y.1731
                        implementations that support event functionality. "
            ::= { hwEthOamCompliances 1 }


        hwEthOamGroups OBJECT IDENTIFIER ::= { hwEthOamConformance 2 }


        hwDot1agCfmMdGroup OBJECT-GROUP
            OBJECTS { hwDot1agCfmMdTableNextIndex, hwDot1agCfmMdFormat, hwDot1agCfmMdName, hwDot1agCfmMdMdLevel, hwDot1agCfmMdMhfCreation,
                hwDot1agCfmMdMhfIdPermission, hwDot1agCfmMdRowStatus }
            STATUS current
            DESCRIPTION
                "Objects for the hwDot1agCfmMd group."
            ::= { hwEthOamGroups 1 }


        hwDot1agCfmMaGroup OBJECT-GROUP
            OBJECTS { hwDot1agCfmMaNextIndex, hwDot1agCfmMaName, hwDot1agCfmMaMapType, hwDot1agCfmMaMapVlanValue, hwDot1agCfmMaMapVsiName,
                hwDot1agCfmMaMapL2vcType, hwDot1agCfmMaMapL2vcValue, hwDot1agCfmMaPktPriority, hwDot1agCfmMaRmepActiveTime, hwDot1agCfmMaMepFngAlarmTime,
                hwDot1agCfmMaMepFngResetTime, hwDot1agCfmMaRowStatus, hwDot1agCfmMaCcmInterval }
            STATUS current
            DESCRIPTION
                "Objects for the hwDot1agCfmMa group."
            ::= { hwEthOamGroups 2 }


        hwDot1agCfmMepGroup OBJECT-GROUP
            OBJECTS { hwDot1agCfmMepIsVlanType, hwDot1agCfmMepIfIndex, hwDot1agCfmMepDot1qVlan, hwDot1agCfmMepPeVlan, hwDot1agCfmMepCeVlan,
                hwDot1agCfmMepDirection, hwDot1agCfmMepCcmSendEnabled, hwDot1agCfmMepMacAddress, hwDot1agCfmMepRowStatus }
            STATUS current
            DESCRIPTION
                "Objects for the hwDot1agCfmMep group."
            ::= { hwEthOamGroups 3 }


        hwDot1agCfmRMepGroup OBJECT-GROUP
            OBJECTS { hwDot1agCfmRMepMacAddress, hwDot1agCfmRMepCcmRecvEnabled, hwDot1agCfmRMepStateIsUp,
                hwDot1agCfmRMepHighestPrDefect, hwDot1agCfmRMepRowStatus }
            STATUS current
            DESCRIPTION
                "RMEP configuration group"
            ::= { hwEthOamGroups 4 }


        hwDot1agCfmMipGroup OBJECT-GROUP
            OBJECTS { hwDot1agCfmMipLevel, hwDot1agCfmMipIfMacAddress }
            STATUS current
            DESCRIPTION
                "MIP configuration group"
            ::= { hwEthOamGroups 5 }


        hwDot1agCfmMacPingGroup OBJECT-GROUP
            OBJECTS { hwDot1agCfmMacPingState, hwDot1agCfmMacPingMdName, hwDot1agCfmMacPingMaName, hwDot1agCfmMacPingMepId, hwDot1agCfmMacPingDestIsMepId,
                hwDot1agCfmMacPingDestMepId, hwDot1agCfmMacPingMacAddress, hwDot1agCfmMacPingOutIfIndex, hwDot1agCfmMacPingTimeOut, hwDot1agCfmMacPingCount,
                hwDot1agCfmMacPingPacketSize, hwDot1agCfmMacPingPriority, hwDot1agCfmMacPingSendPacketNum, hwDot1agCfmMacPingRecvPacketNum,
                hwDot1agCfmMacPingPacketLossRatio, hwDot1agCfmMacPingRecvTimeDelayMin, hwDot1agCfmMacPingRecvTimeDelayMax,
                hwDot1agCfmMacPingRecvTimeDelayAvg, hwDot1agCfmMacPingRowStatus }
            STATUS current
            DESCRIPTION
                "Gmac Ping starting and statistics group"
            ::= { hwEthOamGroups 6 }


        hwDot1agCfmMacTraceGroup OBJECT-GROUP
            OBJECTS { hwDot1agCfmMacTraceState, hwDot1agCfmMacTraceMdName, hwDot1agCfmMacTraceMaName, hwDot1agCfmMacTraceDestIsMepId, hwDot1agCfmMacTraceDestMepId,
                hwDot1agCfmMacTraceMacAddress, hwDot1agCfmMacTraceOutIfIndex, hwDot1agCfmMacTraceTimeOut, hwDot1agCfmMacTraceTTL, hwDot1agCfmMacTraceSendSeqNumber,
                hwDot1agCfmMacTraceResult, hwDot1agCfmMacTraceMepId, hwDot1agCfmMacTraceRowStatus }
            STATUS current
            DESCRIPTION
                "Mac Trace starting and statistics group"
            ::= { hwEthOamGroups 7 }


        hwDot1agCfmMacTraceReplyGroup OBJECT-GROUP
            OBJECTS { hwDot1agCfmMacTraceReplyTTL, hwDot1agCfmMacTraceReplyForwarded, hwDot1agCfmMacTraceReplyTerminalMep, hwDot1agCfmMacTraceReplyRelayAction,
                hwDot1agCfmMacTraceReplyIngressAction, hwDot1agCfmMacTraceReplyIngressMac, hwDot1agCfmMacTraceReplyIngressIfName, hwDot1agCfmMacTraceReplyEgressAction,
                hwDot1agCfmMacTraceReplyEgressMac, hwDot1agCfmMacTraceReplyEgressIfName }
            STATUS current
            DESCRIPTION
                "Gmac Trace starting and statistics group"
            ::= { hwEthOamGroups 8 }


        hwDot1agCfmQueryMdIndexGroup OBJECT-GROUP
            OBJECTS { hwDot1agCfmQueryMdIndex }
            STATUS current
            DESCRIPTION
                "Querying MD index group"
            ::= { hwEthOamGroups 9 }

        hwDot1agCfmQueryMaIndexGroup OBJECT-GROUP
            OBJECTS { hwDot1agCfmQueryMaIndex }
            STATUS current
            DESCRIPTION
                "Querying MA index group"
            ::= { hwEthOamGroups 10 }

        hwDot3ahEfmDetectModeGroup OBJECT-GROUP
            OBJECTS { hwDot3ahEfmEnabled, hwDot3ahEfmDetectMode, hwDot3ahEfmDetectInterval, hwDot3ahEfmDetectMalfunction }
            STATUS current
            DESCRIPTION
                "Test mode group"
            ::= { hwEthOamGroups 11 }


        hwTestMessageGroup OBJECT-GROUP
            OBJECTS { hwTestMessageTableNextIndex, hwTestMessageInterface, hwTestMessageServiceInstance, hwTestMessageMacAddress, hwTestMessageVlanID,
                hwTestMessagePacketSize, hwTestMessageSendPackets, hwTestMessageSendSpeed, hwTestMessageSendEnabled, hwTestMessageSendFinished,
                hwTestMessageRowStatus }
            STATUS current
            DESCRIPTION
                "Test packets setting group"
            ::= { hwEthOamGroups 12 }


        hwTestMessageResultGroup OBJECT-GROUP
            OBJECTS { hwTestMessageResultSendPackets, hwTestMessageResultReceivedPackets, hwTestMessageResultPacketsLost, hwTestMessageResultSendBytes, hwTestMessageResultReceivedBytes,
                hwTestMessageResultBytesLost, hwTestMessageBeginTimeStamp, hwTestMessageEndTimeStamp }
            STATUS current
            DESCRIPTION
                "The group for the tested packets results to be returned."
            ::= { hwEthOamGroups 13 }


        hwEthOamTrapsGroup NOTIFICATION-GROUP
            NOTIFICATIONS { hwDot1agCfmFaultAlarm, hwTestMessageFailed, hwTestMessageCompleted, hwDot3ahEfmThresholdEvent, hwDot3ahEfmNonThresholdEvent, hwDot3ahEfmRemoteDyingGaspEvent,
                            hwDot3ahEfmNonThresholdRecovery, hwCfmVlanOnewayDelay, hwCfmVlanOnewayDelayRecovery, hwCfmVlanTwowayDelay, hwCfmVlanTwowayDelayRecovery, hwDot1agCfmUnexpectedMEGLevel, 
                            hwDot1agCfmUnexpectedMEGLevelCleared, hwDot1agCfmMismerge, hwDot1agCfmMismergeCleared, hwDot1agCfmUnexpectedMEP, hwDot1agCfmUnexpectedMEPCleared, hwDot1agCfmUnexpectedPeriod, 
                            hwDot1agCfmUnexpectedPeriodCleared, hwDot1agCfmUnexpectedMAC, hwDot1agCfmUnexpectedMACCleared, hwDot1agCfmLOC, hwDot1agCfmLOCCleared, hwDot1agCfmExceptionalMACStatus, 
                            hwDot1agCfmExceptionalMACStatusCleared, hwDot1agCfmRDI, hwDot1agCfmRDICleared, hwDot3ahEfmLoopbackFailed, hwY1731AisDefectAlarm, hwY1731AisDefectAlarmRecovery, 
                            hwY1731AisExceedMaxPktNum, hwY1731AisExceedMaxPktNumCleared, hwY1731LckDefect, hwY1731LckDefectCleared, hwY1731Statistic, hwY1731StatisticClear,
			    hwY1731LckExceedThreshold, hwY1731LckExceedThresholdRecovery}
            STATUS current
            DESCRIPTION
                "Objects for the Notifications group.
                A collection of notifications used by Ethernet OAM to signal
                to a management entity that local or remote events have
                occurred on a specified Ethernet link.
                This group is optional for all IEEE 802.3 OAM
                implementations.  Since the information in the notifications
                is dependent on the hwDot3ahEfmEventLogTable, that table must be
                implemented for notifications."
            ::= { hwEthOamGroups 14 }


        hwDot1agCfmGroup OBJECT-GROUP
            OBJECTS { hwDot1agCfmVersion, hwDot1agCfmEnabled }
            STATUS current
            DESCRIPTION
                "Cfm enabling and statistics group"
            ::= { hwEthOamGroups 15 }


        hwDot3ahEfmControlGroup OBJECT-GROUP
            OBJECTS { hwDot3ahEfmAdminState, hwDot3ahEfmOperStatus, hwDot3ahEfmMode, hwDot3ahEfmMaxOamPduSize, hwDot3ahEfmConfigRevision,
                hwDot3ahEfmFunctionsSupported,hwDot3ahEfmTimeout, hwDot3ahEfmInterval }
            STATUS current
            DESCRIPTION
                "A collection of objects providing the abilities,
                configuration, and status of an Ethernet OAM entity.  "
            ::= { hwEthOamGroups 16 }


        hwDot3ahEfmPeerGroup OBJECT-GROUP
            OBJECTS { hwDot3ahEfmPeerMacAddress, hwDot3ahEfmPeerVendorOui, hwDot3ahEfmPeerVendorInfo, hwDot3ahEfmPeerMode, hwDot3ahEfmPeerFunctionsSupported,
                hwDot3ahEfmPeerMaxOamPduSize, hwDot3ahEfmPeerConfigRevision }
            STATUS current
            DESCRIPTION
                "A collection of objects providing the abilities,
                configuration, and status of a peer Ethernet OAM entity.  "
            ::= { hwEthOamGroups 17 }


        hwDot3ahEfmStatsBaseGroup OBJECT-GROUP
            OBJECTS { hwDot3ahEfmInformationTx, hwDot3ahEfmInformationRx, hwDot3ahEfmUniqueEventNotificationTx, hwDot3ahEfmUniqueEventNotificationRx, hwDot3ahEfmDuplicateEventNotificationTx,
                hwDot3ahEfmDuplicateEventNotificationRx, hwDot3ahEfmLoopbackControlTx, hwDot3ahEfmLoopbackControlRx, hwDot3ahEfmVariableRequestTx, hwDot3ahEfmVariableRequestRx,
                hwDot3ahEfmVariableResponseTx, hwDot3ahEfmVariableResponseRx, hwDot3ahEfmOrgSpecificTx, hwDot3ahEfmOrgSpecificRx, hwDot3ahEfmUnsupportedCodesTx,
                hwDot3ahEfmUnsupportedCodesRx, hwDot3ahEfmFramesLostDueToOam }
            STATUS current
            DESCRIPTION
                "A collection of objects providing the statistics for the
                number of various transmit and receive events for OAM on an
                Ethernet like interface.  Note that all of these counters must
                be supported even if the related function (as described in
                hwDot3ahEfmFunctionsSupported) is not supported.  "
            ::= { hwEthOamGroups 18 }


        hwDot3ahEfmLoopbackGroup OBJECT-GROUP
            OBJECTS { hwDot3ahEfmLoopbackStatus, hwDot3ahEfmLoopbackIgnoreRx, hwDot3ahEfmLoopbackTimeout }
            STATUS current
            DESCRIPTION
                "A collection of objects for controlling the OAM remote
                loopback function.  "
            ::= { hwEthOamGroups 19 }


        hwDot3ahEfmErrSymbolPeriodEventGroup OBJECT-GROUP
            OBJECTS { hwDot3ahEfmErrSymPeriodWindowHi, hwDot3ahEfmErrSymPeriodWindowLo, hwDot3ahEfmErrSymPeriodThresholdHi, hwDot3ahEfmErrSymPeriodThresholdLo, hwDot3ahEfmErrSymPeriodEvNotifEnable
                 }
            STATUS current
            DESCRIPTION
                "A collection of objects for configuring the thresholds for an
                Errored Symbol Period Event.

                Each [802.3ah] defined Event Notification TLV has its own
                conformance group because each event can be implemented
                independently of any other.  "
            ::= { hwEthOamGroups 20 }


        hwDot3ahEfmErrFramePeriodEventGroup OBJECT-GROUP
            OBJECTS { hwDot3ahEfmErrFramePeriodWindow, hwDot3ahEfmErrFramePeriodThreshold, hwDot3ahEfmErrFramePeriodEvNotifEnable }
            STATUS current
            DESCRIPTION
                "A collection of objects for configuring the thresholds for an
                Errored Frame Period Event.

                Each [802.3ah] defined Event Notification TLV has its own
                conformance group because each event can be implemented
                independently of any other.  "
            ::= { hwEthOamGroups 21 }


        hwDot3ahEfmErrFrameEventGroup OBJECT-GROUP
            OBJECTS { hwDot3ahEfmErrFrameWindow, hwDot3ahEfmErrFrameThreshold, hwDot3ahEfmErrFrameEvNotifEnable }
            STATUS current
            DESCRIPTION
                "A collection of objects for configuring the thresholds for an
                Errored Frame Event.

                Each [802.3ah] defined Event Notification TLV has its own
                conformance group because each event can be implemented
                independently of any other.  "
            ::= { hwEthOamGroups 22 }


        hwDot3ahEfmErrFrameSecsSummaryEventGroup OBJECT-GROUP
            OBJECTS { hwDot3ahEfmErrFrameSecsSummaryWindow, hwDot3ahEfmErrFrameSecsSummaryThreshold, hwDot3ahEfmErrFrameSecsEvNotifEnable }
            STATUS current
            DESCRIPTION
                "A collection of objects for configuring the thresholds for an
                Errored Frame Seconds Summary Event.

                Each [802.3ah] defined Event Notification TLV has its own
                conformance group because each event can be implemented
                independently of any other.  "
            ::= { hwEthOamGroups 23 }


        hwDot3ahEfmFlagEventGroup OBJECT-GROUP
            OBJECTS { hwDot3ahEfmDyingGaspEnable, hwDot3ahEfmCriticalEventEnable, hwDot3ahEfmThresholdTriggerErrDown }
            STATUS current
            DESCRIPTION
                "A collection of objects for configuring the sending OAMPDUs
                with the critical event flag or dying gasp flag enabled.  "
            ::= { hwEthOamGroups 24 }


        hwDot3ahEfmEventLogGroup OBJECT-GROUP
            OBJECTS { hwDot3ahEfmEventLogTimestamp, hwDot3ahEfmEventLogOui, hwDot3ahEfmEventLogType, hwDot3ahEfmEventLogLocation, hwDot3ahEfmEventLogWindowHi,
                hwDot3ahEfmEventLogWindowLo, hwDot3ahEfmEventLogThresholdHi, hwDot3ahEfmEventLogThresholdLo, hwDot3ahEfmEventLogValue, hwDot3ahEfmEventLogRunningTotal,
                hwDot3ahEfmEventLogEventTotal }
            STATUS current
            DESCRIPTION
                "A collection of objects for configuring the thresholds for an
                Errored Frame Seconds Summary Event and maintaining the event
                information.  "
            ::= { hwEthOamGroups 25 }

        hwDot3ahEfmManagerGroup OBJECT-GROUP
            OBJECTS { hwDot3ahEfmTriggerIfDown, hwDot3ahEfmHoldUpTime }
            STATUS current
            DESCRIPTION
                "hwDot3ahEfmManagerGroup "
            ::= { hwEthOamGroups 26 }

        hwDot3ahEvrrpGroup OBJECT-GROUP
            OBJECTS { hwDot3ahEvrrpCpuState, hwDot3ahEvrrpTriggerIfDown, hwDot3ahEvrrpHoldUpTime }
            STATUS current
            DESCRIPTION
                "A collection of objects for displaying and maintaining
                 the infomation for Evrrp state. "
            ::= { hwEthOamGroups 27 }

        hwY1731BaseConfigGroup OBJECT-GROUP
            OBJECTS { hwY1731PwMeasureMode, hwY1731OneDelayThreshold, hwY1731TwoDelayThreshold }
            STATUS current
            DESCRIPTION
                "A collection of objects for configuring OAM functions for base."
            ::= { hwEthOamGroups 28 }

        hwY1731ConfigGroup OBJECT-GROUP
            OBJECTS { hwY1731RemoteIp, hwY1731VcId, hwY1731MacAddress, hwY1731ResvIndex, hwY1731ServiceType,
                      hwY1731SingleLossRecvEnable, hwY1731OneDelayRecvEnable, hwY1731OneDelayRecvEnableIsContinue, hwY1731TwoDelayRecvEnable,
                      hwY1731SingleLossEnable, hwY1731SingleLossIsContinue, hwY1731SingleLossMepId, hwY1731SingleLossDestIsMepId, hwY1731SingleLossDestMepId,
                      hwY1731SingleLossMacAddress, hwY1731SingleLossInterval, hwY1731SingleLossCount, hwY1731SingleLoss8021pValue,
                      hwY1731DualLossEnable, hwY1731DualLossMepId, hwY1731DualLossDestMepId,
                      hwY1731OneDelayEnable, hwY1731OneDelayIsContinue, hwY1731OneDelayMepId, hwY1731OneDelayDestIsMepId, hwY1731OneDelayDestMepId,
                      hwY1731OneDelayMacAddress, hwY1731OneDelayInterval, hwY1731OneDelayCount, hwY1731OneDelay8021pValue,
                      hwY1731TwoDelayEnable, hwY1731TwoDelayIsContinue, hwY1731TwoDelayMepId, hwY1731TwoDelayDestIsMepId, hwY1731TwoDelayDestMepId,
                      hwY1731TwoDelayMacAddress, hwY1731TwoDelayInterval, hwY1731TwoDelayCount, hwY1731TwoDelay8021pValue,
                      hwY1731SingleLossRecv8021pValue, hwY1731OneDelayRecv8021pValue,hwY1731TwoDelayRecv8021pValue,
                      hwY1731SingleLossRecvMepId, hwY1731OneDelayRecvMepId, hwY1731TwoDelayRecvMepId, hwY1731OneDelayPacketSize, hwY1731TwoDelayPacketSize
                    }
            STATUS current
            DESCRIPTION
                "A collection of objects for configuring OAM functions for performance monitoring."
            ::= { hwEthOamGroups 29 }

        hwY1731AisGroup OBJECT-GROUP
            OBJECTS { hwY1731AisEnable, hwY1731AisSendLevel, hwY1731AisSendInterval, hwY1731AisSendPktStatus, hwY1731AisSuppressEnable,
                      hwY1731AisSuppressStatus }
            STATUS current
            DESCRIPTION
                "A collection of objects for configuring the Alarm Indication Signal (AIS)
                 function to suppress alarms.
                "
            ::= { hwEthOamGroups 30 }


        hwY1731AisVlanGroup OBJECT-GROUP
            OBJECTS { hwY1731AisPeVlan, hwY1731AisLowCeVlan, hwY1731AisHighCeVlan, hwY1731AisLowDot1qVlan, hwY1731AisHighDot1qVlan,
                      hwY1731AisRowStatus }
            STATUS current
            DESCRIPTION
                "A collection of objects for configuring the information about the VLAN
                 that receives AIS frames.
                "
            ::= { hwEthOamGroups 31 }


        hwY1731AisLinkStatusGroup OBJECT-GROUP
            OBJECTS { hwY1731AisLinkRowStatus }
            STATUS current
            DESCRIPTION
                "A collection of objects for configuring sending AIS packets when the
                 status of the interface which is monitored goes down."
            ::= { hwEthOamGroups 32 }

        hwY1731MulPingGroup OBJECT-GROUP
            OBJECTS { hwY1731MulPingState, hwY1731MulPingMdName, hwY1731MulPingMaName, hwY1731MulPingMepId, hwY1731MulPingTimeout,
                hwY1731MulPingCount, hwY1731MulPingPriority, hwY1731MulPingSendPacketNum, hwY1731MulPingRecvPacketNum,
                hwY1731MulPingRecvTimeDelayMin, hwY1731MulPingRecvTimeDelayMax, hwY1731MulPingRecvTimeDelayAvg,  hwY1731MulPingRowStatus }
            STATUS current
            DESCRIPTION
                "A collection of objects for configuring the multicast MAC ping function."
            ::= { hwEthOamGroups 33 }


        hwY1731MulPingReplyGroup OBJECT-GROUP
            OBJECTS { hwY1731MulPingReplyMepId, hwY1731MulPingReplyMacAddress, hwY1731MulPingReplyTransTime }
            STATUS current
            DESCRIPTION
                "A collection of objects for displaying information about
                 the multicast LBRs for responding to the multicast MAC ping operation.
                "
            ::= { hwEthOamGroups 34 }

        hwY1731ResetStatisticGroup OBJECT-GROUP
            OBJECTS { hwY1731ResetStatisticType, hwY1731ResetStatistic8021pValue }
            STATUS current
            DESCRIPTION
                "A collection of objects for reset Y1731 statistic information.
                "
            ::= { hwEthOamGroups 35 }
            
   
        hwY1731ManagerGroup OBJECT-GROUP
            OBJECTS { hwY1731SingleLossStatisticGatherInterval, hwY1731SingleLossLocalStatistic, hwY1731SingleLossLocalRatio,
                      hwY1731SingleLossLocalRatioMax, hwY1731SingleLossLocalRatioMin, hwY1731SingleLossLocalRatioAvg,
                      hwY1731SingleLossRemoteStatistic, hwY1731SingleLossRemoteRatio,
                      hwY1731SingleLossRemoteRatioMax, hwY1731SingleLossRemoteRatioMin, hwY1731SingleLossRemoteRatioAvg,
                      hwY1731OneDelayStatistic, hwY1731OneDelayVariation,
                      hwY1731OneDelayMax, hwY1731OneDelayMin, hwY1731OneDelayAvg,
                      hwY1731TwoDelayStatistic, hwY1731TwoDelayVariation,
                      hwY1731TwoDelayMax, hwY1731TwoDelayMin, hwY1731TwoDelayAvg,
                      hwY1731SingleLossLocalMax, hwY1731SingleLossLocalMin, hwY1731SingleLossLocalAvg, 
                      hwY1731SingleLossRemoteMax, hwY1731SingleLossRemoteMin, hwY1731SingleLossRemoteAvg,
                      hwY1731OneDelayStatisticMax, hwY1731OneDelayStatisticMin, hwY1731OneDelayStatisticAvg, 
                      hwY1731TwoDelayStatisticMax, hwY1731TwoDelayStatisticMin, hwY1731TwoDelayStatisticAvg,hwY1731TwoDelayUnresponsivePacketCount,
                      hwY1731SingleLossStatistic8021pValue, hwY1731OneDelayStatistic8021pValue, hwY1731TwoDelayStatistic8021pValue,
                      hwCfmOneDelayTrapLogMacAddress, hwCfmVlanOneDelayTrapLogTimestamp,
                      hwCfmVlanOneDelayTrapLogDelayValue, hwCfmVlanOneDelayTrapLogDelayValueHigh, hwCfmVlanOneDelayTrapLogDelayValueLow, hwCfmVlanOneDelayTrapLogThreshold,
                      hwCfmOneDelayRecoveryTrapMacAddress, hwCfmVlanOneDelayRecoveryTrapLogTimestamp,
                      hwCfmVlanOneDelayRecoveryTrapLogDelayValue, hwCfmVlanOneDelayRecoveryTrapLogDelayValueHigh, hwCfmVlanOneDelayRecoveryTrapLogDelayValueLow, hwCfmVlanOneDelayRecoveryTrapLogThreshold,
                      hwCfmTwoDelayTrapMacAddress, hwCfmVlanTwoDelayTrapLogTimestamp,
                      hwCfmVlanTwoDelayTrapLogDelayValue, hwCfmVlanTwoDelayTrapLogDelayValueHigh, hwCfmVlanTwoDelayTrapLogDelayValueLow, hwCfmVlanTwoDelayTrapLogThreshold,
                      hwCfmTwoDelayRecoveryTrapMacAddress, hwCfmVlanTwoDelayRecoveryTrapLogTimestamp,
                      hwCfmVlanTwoDelayRecoveryTrapLogDelayValue, hwCfmVlanTwoDelayRecoveryTrapLogDelayValueHigh, hwCfmVlanTwoDelayRecoveryTrapLogDelayValueLow, 
                      hwCfmVlanTwoDelayRecoveryTrapLogThreshold, hwY1731AisMaxPktNum,
                      hwY1731PMModeEnable,hwY1731MaxTestId, hwY1731LckMaxPktNum, hwY1731LckCurrentPktNum, hwY1731LckUpperThreshold, hwY1731LckLowerThreshold
                      }
            STATUS current
            DESCRIPTION
                "Y.1731 detecting group"
            ::= { hwEthOamGroups 36 }

        hwY1731AisVlanConfigGroup OBJECT-GROUP
            OBJECTS { hwY1731AisConfigVlanListLow, hwY1731AisConfigVlanListHigh, hwY1731AisVlanConfigRowStatus }
            STATUS current
            DESCRIPTION
                "A collection of objects for configuring the information about the VLAN
                 that receives AIS frames.
                "
            ::= { hwEthOamGroups 37 }
            
	hwDot1agCfmMPGroup OBJECT-GROUP
            OBJECTS { hwDot1agCfmMPAddressModel }
            STATUS current
            DESCRIPTION
                "Querying MP group"
            ::= { hwEthOamGroups 38 }      
        hwY1731TestIdGroup OBJECT-GROUP
            OBJECTS {  hwY1731TestIdentifier,hwY1731TestIdMdName,hwY1731TestIdMaName,hwY1731TestIdLocalMepId,hwY1731TestIdDestIsMepId,hwY1731TestIdDestMepId,
            hwY1731TestIdDestMepMacAddress,hwY1731TestIdOnwardMacAddress,hwY1731TestIdBackwardMacAddress,hwY1731TestIdIsUpdateOnwardMacAddress,hwY1731TestIdIsUpdateBackwardMacAddress,
            hwY1731TestId8021pValue,hwY1731TestIdUplink8021p,hwY1731TestIdDownlink8021p, hwY1731TestIdDescription,hwY1731TestIdRowStatus }
            STATUS current
            DESCRIPTION
                "A collection of objects for configuring the information about TestId."
            ::= { hwEthOamGroups 39 }   
        hwY1731TestIdSingleEndedLMSendGroup OBJECT-GROUP
            OBJECTS { 
            hwY1731TestIdSingleEndedLMSendIsContinue,hwY1731TestIdSingleEndedLMSendInterval,hwY1731TestIdSingleEndedLMSendCount,hwY1731TestIdSingleEndedLMSendRowStatus }
            STATUS current
            DESCRIPTION
                "A collection of objects for configuring the information about the single-ended ETH-LM sending function."
            ::= { hwEthOamGroups 40 }
        hwY1731TestIdSingleEndedLMReceiveGroup OBJECT-GROUP
            OBJECTS { hwY1731TestIdSingleEndedLMReceiveRowStatus }
            STATUS current
            DESCRIPTION
                "A collection of objects for configuring the information about the single-ended ETH-LM receiving function."
            ::= { hwEthOamGroups 41 }
        hwY1731TestIdOneWayDMSendGroup OBJECT-GROUP
            OBJECTS { hwY1731TestIdOneWayDMSendIsContinue,hwY1731TestIdOneWayDMSendInterval,hwY1731TestIdOneWayDMSendCount,hwY1731TestIdOneWayDMSendPacketSize,hwY1731TestIdOneWayDMSendRowStatus }
            STATUS current
            DESCRIPTION
                "A collection of objects for configuring the information about the one-way ETH-DM sending function."
            ::= { hwEthOamGroups 42 }
        hwY1731TestIdOneWayDMReceiveGroup OBJECT-GROUP
            OBJECTS { hwY1731TestIdOneWayDMReceiveIsContinue,hwY1731TestIdOneWayDMReceiveRowStatus }
            STATUS current
            DESCRIPTION
                "A collection of objects for configuring the information about the one-way ETH-DM receiving function."
            ::= { hwEthOamGroups 43 }
        hwY1731TestIdTwoWayDMSendGroup OBJECT-GROUP
            OBJECTS { hwY1731TestIdTwoWayDMSendIsContinue,hwY1731TestIdTwoWayDMSendInterval,hwY1731TestIdTwoWayDMSendCount,hwY1731TestIdTwoWayDMSendPacketSize,hwY1731TestIdTwoWayDMSendRowStatus }
            STATUS current
            DESCRIPTION
                "A collection of objects for configuring the information about the two-way ETH-DM sending function."
            ::= { hwEthOamGroups 44 }
        hwY1731TestIdTwoWayDMReceiveGroup OBJECT-GROUP
            OBJECTS { hwY1731TestIdTwoWayDMReceiveRowStatus }
            STATUS current
            DESCRIPTION
                "A collection of objects for configuring the information about the two-way ETH-DM receiving function."
            ::= { hwEthOamGroups 45 }


        hwEthOamY1731 OBJECT IDENTIFIER ::= { hwEthOamMib 8 }

        hwY1731ConfigObject OBJECT IDENTIFIER ::= { hwEthOamY1731 1 }

        hwY1731BaseConfigTable OBJECT-TYPE
            SYNTAX SEQUENCE OF HwY1731BaseConfigEntry
            MAX-ACCESS not-accessible
            STATUS current
            DESCRIPTION
                "This table is used to configure OAM functions for base."
            ::= { hwY1731ConfigObject 1 }

        hwY1731BaseConfigEntry OBJECT-TYPE
            SYNTAX HwY1731BaseConfigEntry
            MAX-ACCESS not-accessible
            STATUS current
            DESCRIPTION
                "The configuration entry of base config."
            INDEX { hwDot1agCfmMdIndex, hwDot1agCfmMaIndex }
            ::= { hwY1731BaseConfigTable 1 }

        HwY1731BaseConfigEntry ::=
            SEQUENCE {
                hwY1731PwMeasureMode
                    INTEGER,
                hwY1731OneDelayThreshold
                    Unsigned32,
                hwY1731TwoDelayThreshold
                    Unsigned32
             }

        hwY1731PwMeasureMode OBJECT-TYPE
            SYNTAX INTEGER
                {
                invalid(1),
                symmetry(2),
                asymmetry(3)
                }
            MAX-ACCESS read-write
            STATUS current
            DESCRIPTION
                "This object indicates the PW measure mode.
                 The value can be:
                        invalid
                        symmetry
                        asymmetry
                 If MA associates with a VLAN, the value is invalid.
                 If MA associates with VSI or VLL, the default value is asymmetry.
                "
            ::= { hwY1731BaseConfigEntry 1 }

        hwY1731OneDelayThreshold OBJECT-TYPE
            SYNTAX Unsigned32
            MAX-ACCESS read-write
            STATUS current
            DESCRIPTION
                "This object indicates the alarm threshold for the one-way ETH-DM.
                This object can be set only in VLAN.
                The value ranges from 1 to 4294967295.
                If hwY1731OneDelayThreshold is set to 0, the default alarm threshold of the one-way frame delay is used. By default, no alarm threshold of the one-way frame delay is set.
                "
            ::= { hwY1731BaseConfigEntry 2 }

        hwY1731TwoDelayThreshold OBJECT-TYPE
            SYNTAX Unsigned32
            MAX-ACCESS read-write
            STATUS current
            DESCRIPTION
                "
                This object indicates the alarm threshold for the two-way ETH-DM.
                This object can be set only in VLAN.
                The value ranges from 1 to 4294967295.
                If hwY1731TwoDelayThreshold is set to 0, the default alarm threshold of the two-way frame delay is used. By default, no alarm threshold of the two-way frame delay is set.
                "
            ::= { hwY1731BaseConfigEntry 3 }

        hwY1731ConfigTable OBJECT-TYPE
            SYNTAX SEQUENCE OF HwY1731ConfigEntry
            MAX-ACCESS not-accessible
            STATUS current
            DESCRIPTION
                "This table is used to configure OAM functions for performance monitoring."
            ::= { hwY1731ConfigObject 2 }

        hwY1731ConfigEntry OBJECT-TYPE
            SYNTAX HwY1731ConfigEntry
            MAX-ACCESS not-accessible
            STATUS current
            DESCRIPTION
                "The configuration entry of performance monitoring functions."
            INDEX { hwDot1agCfmMdIndex, hwDot1agCfmMaIndex, hwY1731RemoteIp, hwY1731VcId, hwY1731MacAddress, hwY1731ResvIndex }
            ::= { hwY1731ConfigTable 1 }

        HwY1731ConfigEntry ::=
            SEQUENCE {
                hwY1731RemoteIp
                    IpAddress,
                hwY1731VcId
                    Unsigned32,
                hwY1731MacAddress
                    MacAddress,
                hwY1731ResvIndex
                    Integer32,
                hwY1731ServiceType
                    INTEGER,
                hwY1731SingleLossRecvEnable
                    EnabledStatus,
                hwY1731OneDelayRecvEnable
                    EnabledStatus,
                hwY1731OneDelayRecvEnableIsContinue
                    TruthValue,
                hwY1731TwoDelayRecvEnable
                    EnabledStatus,
                hwY1731SingleLossEnable
                    EnabledStatus,
                hwY1731SingleLossIsContinue
                    TruthValue,
                hwY1731SingleLossMepId
                    Integer32,
                hwY1731SingleLossDestIsMepId
                    TruthValue,
                hwY1731SingleLossDestMepId
                    Integer32,
                hwY1731SingleLossMacAddress
                    MacAddress,
                hwY1731SingleLossInterval
                    INTEGER,
                hwY1731SingleLossCount
                    Integer32,
                hwY1731SingleLoss8021pValue
                    Integer32,
                hwY1731DualLossEnable
                    EnabledStatus,
                hwY1731DualLossMepId
                    Integer32,
                hwY1731DualLossDestMepId
                    Integer32,
                hwY1731OneDelayEnable
                    EnabledStatus,
                hwY1731OneDelayIsContinue
                    TruthValue,
                hwY1731OneDelayMepId
                    Integer32,
                hwY1731OneDelayDestIsMepId
                    TruthValue,
                hwY1731OneDelayDestMepId
                    Integer32,
                hwY1731OneDelayMacAddress
                    MacAddress,
                hwY1731OneDelayInterval
                    INTEGER,
                hwY1731OneDelayCount
                    Integer32,
                hwY1731OneDelay8021pValue
                    Integer32,
                hwY1731TwoDelayEnable
                    EnabledStatus,
                hwY1731TwoDelayIsContinue
                    TruthValue,
                hwY1731TwoDelayMepId
                    Integer32,
                hwY1731TwoDelayDestIsMepId
                    TruthValue,
                hwY1731TwoDelayDestMepId
                    Integer32,
                hwY1731TwoDelayMacAddress
                    MacAddress,
                hwY1731TwoDelayInterval
                    INTEGER,
                hwY1731TwoDelayCount
                    Integer32,
                hwY1731TwoDelay8021pValue
                    Integer32,
                hwY1731SingleLossRecv8021pValue
                    Integer32,
                hwY1731OneDelayRecv8021pValue
                    Integer32,
                hwY1731TwoDelayRecv8021pValue
                    Integer32,
                hwY1731SingleLossRecvMepId
                    Integer32,
                hwY1731OneDelayRecvMepId
                    Integer32,
                hwY1731TwoDelayRecvMepId
                    Integer32,
                hwY1731OneDelayPacketSize
                    Integer32,
                hwY1731TwoDelayPacketSize
                    Integer32
             }

        hwY1731RemoteIp OBJECT-TYPE
            SYNTAX IpAddress
            MAX-ACCESS not-accessible
            STATUS current
            DESCRIPTION
                "This object indicates the IP address of the remote end."
            ::= { hwY1731ConfigEntry 1 }

        hwY1731VcId OBJECT-TYPE
            SYNTAX Unsigned32
            MAX-ACCESS not-accessible
            STATUS current
            DESCRIPTION
                "This object indicates the VC ID."
            ::= { hwY1731ConfigEntry 2 }

        hwY1731MacAddress OBJECT-TYPE
            SYNTAX MacAddress
            MAX-ACCESS not-accessible
            STATUS current
            DESCRIPTION
                "This object indicates the MAC address of the remote end."
            ::= { hwY1731ConfigEntry 3 }

        hwY1731ResvIndex OBJECT-TYPE
            SYNTAX Integer32
            MAX-ACCESS not-accessible
            STATUS current
            DESCRIPTION
                "This object indicates the index for reserve."
            ::= { hwY1731ConfigEntry 4 }

        hwY1731ServiceType OBJECT-TYPE
            SYNTAX INTEGER
                {
                vlan(1),
                vsi(2),
                vll(3),
                unknown(4),
                unbind(5)
                }
            MAX-ACCESS read-only
            STATUS current
            DESCRIPTION
                "This object indicates the type of service.
                 The service can be:
                        vlan
                        vsi
                        vll
                        unbind
                "
            ::= { hwY1731ConfigEntry 5 }

        hwY1731SingleLossRecvEnable OBJECT-TYPE
            SYNTAX EnabledStatus
            MAX-ACCESS read-create
            STATUS current
            DESCRIPTION
                "This object indicates whether the single-ended ETH-LM receiving is enabled on the MEP
                 in the MA to implement the single-ended ETH-LM.
                 The value can be:
                        enabled
                        disabled
                 By default, the value is disabled."
            ::= { hwY1731ConfigEntry 6 }

        hwY1731OneDelayRecvEnable OBJECT-TYPE
            SYNTAX EnabledStatus
            MAX-ACCESS read-create
            STATUS current
            DESCRIPTION
                "This object indicates whether the one-way ETH-DM receiving is enabled on the MEP
                 in the MA to implement the one-way ETH-DM.
                 The value can be:
                        enabled
                        disabled
                 By default, the value is disabled."
            ::= { hwY1731ConfigEntry 7 }

        hwY1731OneDelayRecvEnableIsContinue OBJECT-TYPE
            SYNTAX TruthValue
            MAX-ACCESS read-create
            STATUS current
            DESCRIPTION
                "This object indicates whether the one-way ETH-DM receiving is continual."
            ::= { hwY1731ConfigEntry 8 }

        hwY1731TwoDelayRecvEnable OBJECT-TYPE
            SYNTAX EnabledStatus
            MAX-ACCESS read-create
            STATUS current
            DESCRIPTION
                "This object indicates whether the two-way ETH-DM receiving is enabled on the MEP
                 in the MA to implement the two-way ETH-DM.
                 The value can be:
                        enabled
                        disabled
                 By default, the value is disabled.
                "
            ::= { hwY1731ConfigEntry 9 }

        hwY1731SingleLossEnable OBJECT-TYPE
            SYNTAX EnabledStatus
            MAX-ACCESS read-create
            STATUS current
            DESCRIPTION
                "This object indicates whether the single-ended ETH-LM sending is enabled.
                 The value can be:
                        enabled
                        disabled
                 By default, the value is disabled.
                "
            ::= { hwY1731ConfigEntry 10 }

        hwY1731SingleLossIsContinue OBJECT-TYPE
            SYNTAX TruthValue
            MAX-ACCESS read-create
            STATUS current
            DESCRIPTION
                "This object indicates whether the single-ended ETH-LM sending is continual.
                 If the value is 'false', it indicates that the single-ended ETH-LM is on-demand.
                "
            ::= { hwY1731ConfigEntry 11 }

        hwY1731SingleLossMepId OBJECT-TYPE
            SYNTAX Integer32 (0 | 1..8191)
            MAX-ACCESS read-create
            STATUS current
            DESCRIPTION
                "This object indicates the ID of the local MEP that is specified 
                 in the single-ended ETH-LM operation.
                 The value can be 0 or ranges from 1 to 8191.
                 The value 0 is an invalid value.
                "
            ::= { hwY1731ConfigEntry 12 }

        hwY1731SingleLossDestIsMepId OBJECT-TYPE
            SYNTAX TruthValue
            MAX-ACCESS read-create
            STATUS current
            DESCRIPTION
                "This object indicates whether the destination MAC address of 
                the single-ended ETH-LM is the specified RMEP's MAC address.
                "
            ::= { hwY1731ConfigEntry 13 }

        hwY1731SingleLossDestMepId OBJECT-TYPE
            SYNTAX Integer32 (0 | 1..8191)
            MAX-ACCESS read-create
            STATUS current
            DESCRIPTION
                "This object indicates the ID of the remote MEP that is specified 
                 in the single-ended ETH-LM operation.
                 The value 0 is an invalid value.
                "
            ::= { hwY1731ConfigEntry 14 }

        hwY1731SingleLossMacAddress OBJECT-TYPE
            SYNTAX MacAddress
            MAX-ACCESS read-create
            STATUS current
            DESCRIPTION
                "This object indicates the MAC address of the remote end."
            ::= { hwY1731ConfigEntry 15 }

        hwY1731SingleLossInterval OBJECT-TYPE
            SYNTAX INTEGER
                {
                invalid(1),
                interval1s(2),
                interval10s(3),
                interval30s(4)
                }
            MAX-ACCESS read-create
            STATUS current
            DESCRIPTION
                "This object indicates the interval of the sent LMM frames.
                 When on-demand OAM, the value can be:
                    1 second
                    10 seconds
                 When proactive OAM, the value can be:
                    1 second
                    10 seconds
                    30 seconds
                "
            ::= { hwY1731ConfigEntry 16 }

        hwY1731SingleLossCount OBJECT-TYPE
            SYNTAX Integer32 (0 | 1..60)
            MAX-ACCESS read-create
            STATUS current
            DESCRIPTION
                "This object indicates the number of LMM frames to be sent.
                 The value can be 0 or ranges from 1 to 60.
                 When proactive OAM, the value is 0."
            ::= { hwY1731ConfigEntry 17 }

        hwY1731SingleLoss8021pValue OBJECT-TYPE
            SYNTAX Integer32 (0 | 1..255)
            MAX-ACCESS read-create
            STATUS current
            DESCRIPTION
                "This object indicates the 802.1p priority of the sent LMM packets.
                The priority value ranges from 0 to 7. It maps a 8 bits number.
                0 - 1  (0x01)
                1 - 2  (0x02)
                2 - 4  (0x04)
                3 - 8  (0x08)
                4 - 16 (0x10)
                5 - 32 (0x20)
                6 - 64 (0x40)
                7 - 128(0x80)
                For example, if 802.1p priority is 0 , 4 , 7, the value is 145(1 + 16 + 128).
                The value 0 indicates that the priority is not set.
                "
            ::= { hwY1731ConfigEntry 18 }

        hwY1731DualLossEnable OBJECT-TYPE
            SYNTAX EnabledStatus
            MAX-ACCESS read-create
            STATUS current
            DESCRIPTION
                "This object indicates whether the dual-ended ETH-LM is enabled.
                 The value can be:
                    enabled
                    disabled
                 By default, the value is disabled.
                "
            ::= { hwY1731ConfigEntry 19 }

        hwY1731DualLossMepId OBJECT-TYPE
            SYNTAX Integer32 (0 | 1..8191)
            MAX-ACCESS read-create
            STATUS current
            DESCRIPTION
                "This object indicates the ID of the local MEP that is specified 
                 in the dual-ended ETH-LM operation.
                 The value can be 0 or ranges from 1 to 8191.
                 The value 0 is an invalid value.
                "
            ::= { hwY1731ConfigEntry 20 }

        hwY1731DualLossDestMepId OBJECT-TYPE
            SYNTAX Integer32 (0 | 1..8191)
            MAX-ACCESS read-create
            STATUS current
            DESCRIPTION
                "This object indicates the ID of the remote MEP that is specified 
                 in the dual-ended ETH-LM operation.
                 The value can be 0 or ranges from 1 to 8191.
                 The value 0 is an invalid value.
                "
            ::= { hwY1731ConfigEntry 21 }

        hwY1731OneDelayEnable OBJECT-TYPE
            SYNTAX EnabledStatus
            MAX-ACCESS read-create
            STATUS current
            DESCRIPTION
                "This object indicates whether the one-way ETH-DM sending is enabled.
                 The value can be:
                    enabled
                    disabled
                 By default, the value is disabled.
                "
            ::= { hwY1731ConfigEntry 22 }

        hwY1731OneDelayIsContinue OBJECT-TYPE
            SYNTAX TruthValue
            MAX-ACCESS read-create
            STATUS current
            DESCRIPTION
                "This object indicates whether the one-way ETH-DM sending is continual.
                 If the value is 'false', it indicates that the one-way ETH-DM is on-demand.
                "
            ::= { hwY1731ConfigEntry 23 }

        hwY1731OneDelayMepId OBJECT-TYPE
            SYNTAX Integer32 (0 | 1..8191)
            MAX-ACCESS read-create
            STATUS current
            DESCRIPTION
                "This object indicates the ID of the local MEP that is specified 
                 in the one-way ETH-DM operation.
                 The value can be 0 or ranges from 1 to 8191.
                 The value 0 is an invalid value.
                "
            ::= { hwY1731ConfigEntry 24 }

        hwY1731OneDelayDestIsMepId OBJECT-TYPE
            SYNTAX TruthValue
            MAX-ACCESS read-create
            STATUS current
            DESCRIPTION
                "This object indicates whether the destination MAC address of 
                 the one-way ETH-DM is the specified RMEP's MAC address.
                "
            ::= { hwY1731ConfigEntry 25 }

        hwY1731OneDelayDestMepId OBJECT-TYPE
            SYNTAX Integer32 (0 | 1..8191)
            MAX-ACCESS read-create
            STATUS current
            DESCRIPTION
                "This object indicates the ID of the remote MEP that is specified 
                 in the one-way ETH-DM operation.
                 The value can be 0 or ranges from 1 to 8191.
                 The value 0 is an invalid value.
                "
            ::= { hwY1731ConfigEntry 26 }

        hwY1731OneDelayMacAddress OBJECT-TYPE
            SYNTAX MacAddress
            MAX-ACCESS read-create
            STATUS current
            DESCRIPTION
                "This object indicates the MAC address of the RMEP."
            ::= { hwY1731ConfigEntry 27 }

        hwY1731OneDelayInterval OBJECT-TYPE
            SYNTAX INTEGER
                {
                invalid(1),
                interval1s(2),
                interval10s(3),
                interval30s(4)
                }
            MAX-ACCESS read-create
            STATUS current
            DESCRIPTION
                "This object indicates the interval of the sent 1DM frames.
                 When on-demand OAM, the value can be:
                    1 second
                    10 seconds
                 When proactive OAM, the value can be:
                    1 second
                    10 seconds
                    30 seconds
                "
            ::= { hwY1731ConfigEntry 28 }

        hwY1731OneDelayCount OBJECT-TYPE
            SYNTAX Integer32 (0 | 1..60)
            MAX-ACCESS read-create
            STATUS current
            DESCRIPTION
                "This object indicates the number of the sent 1DM frames.
                 The value can be 0 or ranges from 1 to 60.
                 When proactive OAM, the value is 0."
            ::= { hwY1731ConfigEntry 29 }

        hwY1731OneDelay8021pValue OBJECT-TYPE
            SYNTAX Integer32 (0 | 1..255)
            MAX-ACCESS read-create
            STATUS current
            DESCRIPTION
                "This object indicates the 802.1p priority of the sent 1DM packets.
                The priority value ranges from 0 to 7. It maps a 8 bits number.
                0 - 1  (0x01)
                1 - 2  (0x02)
                2 - 4  (0x04)
                3 - 8  (0x08)
                4 - 16 (0x10)
                5 - 32 (0x20)
                6 - 64 (0x40)
                7 - 128(0x80)
                For example, if 802.1p priority is 0, 4 , 7, the value is 145(1 + 16 + 128).
                The value 0 indicates that the priority is not set.
                "
            ::= { hwY1731ConfigEntry 30 }

        hwY1731TwoDelayEnable OBJECT-TYPE
            SYNTAX EnabledStatus
            MAX-ACCESS read-create
            STATUS current
            DESCRIPTION
                "This object indicates whether the two-way ETH-DM sending is enabled.
                "
            ::= { hwY1731ConfigEntry 31 }

        hwY1731TwoDelayIsContinue OBJECT-TYPE
            SYNTAX TruthValue
            MAX-ACCESS read-create
            STATUS current
            DESCRIPTION
                "This object indicates whether the two-way ETH-DM sending is continual.
                 If the value is 'false', it indicates that the two-way ETH-DM is on-demand.
                "
            ::= { hwY1731ConfigEntry 32 }

        hwY1731TwoDelayMepId OBJECT-TYPE
            SYNTAX Integer32 (0 | 1..8191)
            MAX-ACCESS read-create
            STATUS current
            DESCRIPTION
                "This object indicates the ID of the local MEP that is specified 
                 in the two-way ETH-DM operation.
                 The value can be 0 or ranges from 1 to 8191.
                 The value 0 is an invalid value.
                "
            ::= { hwY1731ConfigEntry 33 }

        hwY1731TwoDelayDestIsMepId OBJECT-TYPE
            SYNTAX TruthValue
            MAX-ACCESS read-create
            STATUS current
            DESCRIPTION
                "This object indicates whether the destination MAC address of 
                 the two-way ETH-DM is the specified RMEP's MAC address.
                "
            ::= { hwY1731ConfigEntry 34}

        hwY1731TwoDelayDestMepId OBJECT-TYPE
            SYNTAX Integer32 (0 | 1..8191)
            MAX-ACCESS read-create
            STATUS current
            DESCRIPTION
                "This object indicates the ID of the remote MEP that is specified 
                 in the two-way ETH-DM operation.
                 The value can be 0 or ranges from 1 to 8191.
                 The value 0 is an invalid value."
            ::= { hwY1731ConfigEntry 35 }

        hwY1731TwoDelayMacAddress OBJECT-TYPE
            SYNTAX MacAddress
            MAX-ACCESS read-create
            STATUS current
            DESCRIPTION
                "This object indicates the destination MAC address."
            ::= { hwY1731ConfigEntry 36 }

        hwY1731TwoDelayInterval OBJECT-TYPE
            SYNTAX INTEGER
                {
                invalid(1),
                interval1s(2),
                interval10s(3),
                interval30s(4)
                }
            MAX-ACCESS read-create
            STATUS current
            DESCRIPTION
                "This object indicates the interval of the sent DMM frames.
                 When on-demand OAM, the value can be:
                    1 second
                    10 seconds
                 When proactive OAM, the value can be:
                    1 second
                    10 seconds
                    30 seconds
                "
            ::= { hwY1731ConfigEntry 37 }

        hwY1731TwoDelayCount OBJECT-TYPE
            SYNTAX Integer32 (0 | 1..60)
            MAX-ACCESS read-create
            STATUS current
            DESCRIPTION
                "This object indicates the number of the sent DMM frames.
                 The value can be 0 or ranges from 1 to 60.
                 When proactive OAM, the value is 0."
            ::= { hwY1731ConfigEntry 38 }

        hwY1731TwoDelay8021pValue OBJECT-TYPE
            SYNTAX Integer32 (0 | 1..255)
            MAX-ACCESS read-create
            STATUS current
            DESCRIPTION
                "This object indicates the 802.1p priority of the sent DMM packets.
                The priority value ranges from 0 to 7. It maps a 8 bits number.
                0 - 1  (0x01)
                1 - 2  (0x02)
                2 - 4  (0x04)
                3 - 8  (0x08)
                4 - 16 (0x10)
                5 - 32 (0x20)
                6 - 64 (0x40)
                7 - 128(0x80)
                For example, if 802.1p priority is 0 , 4 , 7, the value is 145(1 + 16 + 128).
                The value 0 indicates that the priority is not set.
                "
            ::= { hwY1731ConfigEntry 39 }

        hwY1731SingleLossRecv8021pValue OBJECT-TYPE
            SYNTAX Integer32 (0 | 1..255)
            MAX-ACCESS read-create
            STATUS current
            DESCRIPTION
                "This object indicates the 802.1p priority of the received LMM packets.
                The priority value ranges from 0 to 7. It maps a 8 bits number.
                0 - 1  (0x01)
                1 - 2  (0x02)
                2 - 4  (0x04)
                3 - 8  (0x08)
                4 - 16 (0x10)
                5 - 32 (0x20)
                6 - 64 (0x40)
                7 - 128(0x80)
                For example, if 802.1p priority is 0 , 4 , 7, the value is 145(1 + 16 + 128).
                The value 0 indicates that the priority is not set.
                "
            ::= { hwY1731ConfigEntry 40 }

        hwY1731OneDelayRecv8021pValue OBJECT-TYPE
            SYNTAX Integer32 (0 | 1..255)
            MAX-ACCESS read-create
            STATUS current
            DESCRIPTION
                "This object indicates the 802.1p priority of the received 1DM packets.
                The priority value ranges from 0 to 7. It maps a 8 bits number.
                0 - 1  (0x01)
                1 - 2  (0x02)
                2 - 4  (0x04)
                3 - 8  (0x08)
                4 - 16 (0x10)
                5 - 32 (0x20)
                6 - 64 (0x40)
                7 - 128(0x80)
                For example, if 802.1p priority is 0 , 4 , 7, the value is 145(1 + 16 + 128).
                The value 0 indicates that the priority is not set.
                "
            ::= { hwY1731ConfigEntry 41 }

        hwY1731TwoDelayRecv8021pValue OBJECT-TYPE
            SYNTAX Integer32 (0 | 1..255)
            MAX-ACCESS read-create
            STATUS current
            DESCRIPTION
                "This object indicates the 802.1p priority of the received DMM packets.
                The priority value ranges from 0 to 7. It maps a 8 bits number.
                0 - 1  (0x01)
                1 - 2  (0x02)
                2 - 4  (0x04)
                3 - 8  (0x08)
                4 - 16 (0x10)
                5 - 32 (0x20)
                6 - 64 (0x40)
                7 - 128(0x80)
                For example, if 802.1p priority is 0 , 4 , 7, the value is 145(1 + 16 + 128).
                The value 0 indicates that the priority is not set.
                "
            ::= { hwY1731ConfigEntry 42 }

        hwY1731SingleLossRecvMepId OBJECT-TYPE
            SYNTAX Integer32 (0 | 1..8191)
            MAX-ACCESS read-create
            STATUS current
            DESCRIPTION
                "This object indicates the ID of the local MEP.
                 The value can be 0 or ranges from 1 to 8191.
                 The value 0 is an invalid value.
                "
            ::= { hwY1731ConfigEntry 43 }

        hwY1731OneDelayRecvMepId OBJECT-TYPE
            SYNTAX Integer32 (0 | 1..8191)
            MAX-ACCESS read-create
            STATUS current
            DESCRIPTION
                "This object indicates the ID of the local MEP.
                 The value can be 0 or ranges from 1 to 8191.
                 The value 0 is an invalid value.
                "
            ::= { hwY1731ConfigEntry 44 }

        hwY1731TwoDelayRecvMepId OBJECT-TYPE
            SYNTAX Integer32 (0 | 1..8191)
            MAX-ACCESS read-create
            STATUS current
            DESCRIPTION
                "This object indicates the ID of the local MEP.
                 The value can be 0 or ranges from 1 to 8191.
                 The value 0 is an invalid value.
                "
            ::= { hwY1731ConfigEntry 45 }
            
        hwY1731OneDelayPacketSize OBJECT-TYPE
            SYNTAX Integer32 (0 | 64..1518)
            MAX-ACCESS read-create
            STATUS current
            DESCRIPTION
                "This object indicates the size of one-way ETH-DM packet.
                 The value can be 0 or ranges from 64 to 1518.
                 The value 0 means that the packet size is not specified.
                 By default, the value is 0.
                "
            ::= { hwY1731ConfigEntry 46 }
        
        hwY1731TwoDelayPacketSize OBJECT-TYPE
            SYNTAX Integer32 (0 | 64..1518)
            MAX-ACCESS read-create
            STATUS current
            DESCRIPTION
                "This object indicates the size of a two-way ETH-DM packet.
                 The value can be 0 or ranges from 64 to 1518.
                 The value 0 means that the packet size is not specified.
                 By default, the value is 0.
                "
            ::= { hwY1731ConfigEntry 47 }

        hwY1731AisTable OBJECT-TYPE
            SYNTAX SEQUENCE OF HwY1731AisEntry
            MAX-ACCESS not-accessible
            STATUS current
            DESCRIPTION
                "This table is used to configure the Alarm Indication Signal (AIS)
                 function to suppress alarms.
                "
            ::= { hwY1731ConfigObject 3 }


        hwY1731AisEntry OBJECT-TYPE
            SYNTAX HwY1731AisEntry
            MAX-ACCESS not-accessible
            STATUS current
            DESCRIPTION
                "The entry of alarm indication signal."
            INDEX { hwDot1agCfmMdIndex, hwDot1agCfmMaIndex }
            ::= { hwY1731AisTable 1 }


        HwY1731AisEntry ::=
            SEQUENCE {
                hwY1731AisEnable
                    EnabledStatus,
                hwY1731AisSendLevel
                    Integer32,
                hwY1731AisSendInterval
                    INTEGER,
                hwY1731AisSendPktStatus
                    EnabledStatus,
                hwY1731AisSuppressEnable
                    EnabledStatus,
                hwY1731AisSuppressStatus
                    EnabledStatus
             }

        hwY1731AisEnable OBJECT-TYPE
            SYNTAX EnabledStatus
            MAX-ACCESS read-create
            STATUS current
            DESCRIPTION
                "This object indicates whether the AIS function is enabled in
                 the current MA. The value of this object can be:
                    enabled
                    disabled
                 By default, the value is disabled.
                "
            ::= { hwY1731AisEntry 1 }


        hwY1731AisSendLevel OBJECT-TYPE
            SYNTAX Integer32 (-1 | 0..7)
            MAX-ACCESS read-create
            STATUS current
            DESCRIPTION
                "This object indicates the level of the sent AIS frames.
                 The value can be -1 or ranges from 0 to 7.
                 The value -1 is an invalid value.
                "
            ::= { hwY1731AisEntry 2 }


        hwY1731AisSendInterval OBJECT-TYPE
            SYNTAX INTEGER
                {
                interval1s(1),
                interval60s(2)
                }
            MAX-ACCESS read-create
            STATUS current
            DESCRIPTION
                "This object indicates the interval of the sent AIS frames.
                 The value can be:
                    1 second
                    60 seconds
                 The default value is 1 second.
                "
            DEFVAL { interval1s }
            ::= { hwY1731AisEntry 3 }


        hwY1731AisSendPktStatus OBJECT-TYPE
            SYNTAX EnabledStatus
            MAX-ACCESS read-only
            STATUS current
            DESCRIPTION
                "This object indicates whether the current MA is sending AIS frames.
                 The value can be:
                    enabled
                    disabled
                 By default, the value is disabled.
                "
            ::= { hwY1731AisEntry 4 }


        hwY1731AisSuppressEnable OBJECT-TYPE
            SYNTAX EnabledStatus
            MAX-ACCESS read-create
            STATUS current
            DESCRIPTION
                "This object indicates whether the alarm suppression function is enabled.
                 The value can be:
                    enabled
                    disabled
                 By default, the value is disabled.
                "
            ::= { hwY1731AisEntry 5 }


        hwY1731AisSuppressStatus OBJECT-TYPE
            SYNTAX EnabledStatus
            MAX-ACCESS read-only
            STATUS current
            DESCRIPTION
                "This object indicates whether the alarm function on the current
                 device is in the suppression state. The value can be:
                    enabled
                    disabled
                "
            ::= { hwY1731AisEntry 6 }


        hwY1731AisVlanTable OBJECT-TYPE
            SYNTAX SEQUENCE OF HwY1731AisVlanEntry
            MAX-ACCESS not-accessible
            STATUS current
            DESCRIPTION
                "This table is used to configure the information about the VLAN that
                 receives AIS frames.
                "
            ::= { hwY1731ConfigObject 4 }


        hwY1731AisVlanEntry OBJECT-TYPE
            SYNTAX HwY1731AisVlanEntry
            MAX-ACCESS not-accessible
            STATUS current
            DESCRIPTION
                "The entry of alarm indication signal about vlan infomation."
            INDEX { hwDot1agCfmMdIndex, hwDot1agCfmMaIndex, hwDot1agCfmMepIdentifier }
            ::= { hwY1731AisVlanTable 1 }


        HwY1731AisVlanEntry ::=
            SEQUENCE {
                hwY1731AisPeVlan
                    VlanIdOrNone,
                hwY1731AisLowCeVlan
                    VlanIdOrNone,
                hwY1731AisHighCeVlan
                    VlanIdOrNone,
                hwY1731AisLowDot1qVlan
                    VlanIdOrNone,
                hwY1731AisHighDot1qVlan
                    VlanIdOrNone,
                hwY1731AisRowStatus
                    RowStatus
             }

        hwY1731AisPeVlan OBJECT-TYPE
            SYNTAX VlanIdOrNone
            MAX-ACCESS read-create
            STATUS current
            DESCRIPTION
                "This object indicates the ID of the PE VLAN corresponding to
                 the AIS function.
                "
            ::= { hwY1731AisVlanEntry 1 }


        hwY1731AisLowCeVlan OBJECT-TYPE
            SYNTAX VlanIdOrNone
            MAX-ACCESS read-create
            STATUS current
            DESCRIPTION
                "
                This object indicates the lower limit of the ID of the CE VLAN
                corresponding to the AIS function.
                "
            ::= { hwY1731AisVlanEntry 2 }


        hwY1731AisHighCeVlan OBJECT-TYPE
            SYNTAX VlanIdOrNone
            MAX-ACCESS read-create
            STATUS current
            DESCRIPTION
                "This object indicates the upper limit of the ID of the CE VLAN
                 corresponding to the AIS function.
                "
            ::= { hwY1731AisVlanEntry 3 }


        hwY1731AisLowDot1qVlan OBJECT-TYPE
            SYNTAX VlanIdOrNone
            MAX-ACCESS read-create
            STATUS current
            DESCRIPTION
                "This object indicates the lower limit of the ID of the dot1q VLAN
                 corresponding to the AIS function.
                "
            ::= { hwY1731AisVlanEntry 4 }


        hwY1731AisHighDot1qVlan OBJECT-TYPE
            SYNTAX VlanIdOrNone
            MAX-ACCESS read-create
            STATUS current
            DESCRIPTION
                "This object indicates the upper limit of the ID of the dot1q VLAN
                 corresponding to the AIS function.
                "
            ::= { hwY1731AisVlanEntry 5 }


        hwY1731AisRowStatus OBJECT-TYPE
            SYNTAX RowStatus
            MAX-ACCESS read-create
            STATUS current
            DESCRIPTION
                "This object indicates the row status of this table.

                 The writable columns in a row can not be changed if the row
                 is active. All columns MUST have a valid value before a row
                 can be activated."
            ::= { hwY1731AisVlanEntry 99 }


        hwY1731AisLinkStatusTable OBJECT-TYPE
            SYNTAX SEQUENCE OF HwY1731AisLinkStatusEntry
            MAX-ACCESS not-accessible
            STATUS current
            DESCRIPTION
                "
                This table is used to enable Y.1731 to send AIS packets when the status of the interface which is monitored goes down.
                "
            ::= { hwY1731ConfigObject 5 }

        hwY1731AisLinkStatusEntry OBJECT-TYPE
            SYNTAX HwY1731AisLinkStatusEntry
            MAX-ACCESS not-accessible
            STATUS current
            DESCRIPTION
                "The entry of AIS monitoring the link status of the interface."
            INDEX { hwDot1agCfmMdIndex, hwDot1agCfmMaIndex, hwY1731AisLinkStatusIfIndex }
            ::= { hwY1731AisLinkStatusTable 1 }

        HwY1731AisLinkStatusEntry ::=
            SEQUENCE {
                hwY1731AisLinkStatusIfIndex
                    InterfaceIndex,
                hwY1731AisLinkRowStatus
                    RowStatus
             }

        hwY1731AisLinkStatusIfIndex OBJECT-TYPE
            SYNTAX InterfaceIndex
            MAX-ACCESS not-accessible
            STATUS current
            DESCRIPTION
                "This object indicates the index of the interface which is monitored by AIS."
            ::= { hwY1731AisLinkStatusEntry 1 }

        hwY1731AisLinkRowStatus OBJECT-TYPE
            SYNTAX RowStatus
            MAX-ACCESS read-create
            STATUS current
            DESCRIPTION
                "This object indicates the row status of this table.

                The writable columns in a row can not be changed if the row
                is active. All columns MUST have a valid value before a row
                can be activated."
            ::= { hwY1731AisLinkStatusEntry 20 }

        hwY1731MulPingTable OBJECT-TYPE
            SYNTAX SEQUENCE OF HwY1731MulPingEntry
            MAX-ACCESS not-accessible
            STATUS current
            DESCRIPTION
                "This table is used to configure the multicast MAC ping function."
            ::= { hwY1731ConfigObject 6 }


        hwY1731MulPingEntry OBJECT-TYPE
            SYNTAX HwY1731MulPingEntry
            MAX-ACCESS not-accessible
            STATUS current
            DESCRIPTION
                "The entry of multicast ping."
            INDEX { hwY1731MulPingIndex }
            ::= { hwY1731MulPingTable 1 }


        HwY1731MulPingEntry ::=
            SEQUENCE {
                hwY1731MulPingIndex
                    Unsigned32,
                hwY1731MulPingState
                    EnabledStatus,
                hwY1731MulPingMdName
                    OCTET STRING,
                hwY1731MulPingMaName
                    OCTET STRING,
                hwY1731MulPingMepId
                    Integer32,
                hwY1731MulPingTimeout
                    Unsigned32,
                hwY1731MulPingCount
                    Unsigned32,
                hwY1731MulPingPriority
                    Integer32,
                hwY1731MulPingSendPacketNum
                    Counter32,
                hwY1731MulPingRecvPacketNum
                    Counter32,
                hwY1731MulPingRecvTimeDelayMin
                    Unsigned32,
                hwY1731MulPingRecvTimeDelayMax
                    Unsigned32,
                hwY1731MulPingRecvTimeDelayAvg
                    Unsigned32,
                hwY1731MulPingRowStatus
                    RowStatus
             }

        hwY1731MulPingIndex OBJECT-TYPE
            SYNTAX Unsigned32
            MAX-ACCESS not-accessible
            STATUS current
            DESCRIPTION
                "This object indicates the index of this table."
            ::= { hwY1731MulPingEntry 1 }


        hwY1731MulPingState OBJECT-TYPE
            SYNTAX EnabledStatus
            MAX-ACCESS read-create
            STATUS current
            DESCRIPTION
                "This object indicates whether the multicast MAC ping function is enabled.
                 The value can be:
                    enabled
                    disabled
                 By default, the value is disabled.
                "
            ::= { hwY1731MulPingEntry 2 }


        hwY1731MulPingMdName OBJECT-TYPE
            SYNTAX OCTET STRING (SIZE (1..43))
            MAX-ACCESS read-create
            STATUS current
            DESCRIPTION
                "This object indicates the name of the MD that initiates the multicast MAC ping."
            ::= { hwY1731MulPingEntry 3 }


        hwY1731MulPingMaName OBJECT-TYPE
            SYNTAX OCTET STRING (SIZE (1..43))
            MAX-ACCESS read-create
            STATUS current
            DESCRIPTION
                "This object indicates the name of the MA that initiates the multicast MAC ping."
            ::= { hwY1731MulPingEntry 4 }


        hwY1731MulPingMepId OBJECT-TYPE
            SYNTAX Integer32 (0 | 1..8191)
            MAX-ACCESS read-create
            STATUS current
            DESCRIPTION
                "This object indicates the ID of the local MEP of the 802.1ag
                 MAC multicast ping operation.
                 The value ranges from 1 to 8191.
                 By default, the value is 0.
                "
            DEFVAL { 0 }
            ::= { hwY1731MulPingEntry 5 }


        hwY1731MulPingTimeout OBJECT-TYPE
            SYNTAX Unsigned32 (1..65535)
            MAX-ACCESS read-create
            STATUS current
            DESCRIPTION
                "This object indicates the timeout period of the multicast MAC ping.
                 The value ranges from 1 to 65535, in milliseconds.
                 By default, the value is 5000.
                "
            DEFVAL { 5000 }
            ::= { hwY1731MulPingEntry 6 }


        hwY1731MulPingCount OBJECT-TYPE
            SYNTAX Unsigned32 (1..4294967295)
            MAX-ACCESS read-create
            STATUS current
            DESCRIPTION
                "This object indicates the number of the sent multicast LBM packets.
                 By default, the value is 3.
                "
            DEFVAL { 3 }
            ::= { hwY1731MulPingEntry 7 }


        hwY1731MulPingPriority OBJECT-TYPE
            SYNTAX Integer32 (0..7 | 255)
            MAX-ACCESS read-create
            STATUS current
            DESCRIPTION
                "This object indicates the priority of the sent LBM packets.
                 The value ranges from 0 to 7 or can be 255. The value 255 is an invalid value.
                 The greater the value is, the higher the priority is.
                "
            DEFVAL { 255 }
            ::= { hwY1731MulPingEntry 8 }


        hwY1731MulPingSendPacketNum OBJECT-TYPE
            SYNTAX Counter32
            MAX-ACCESS read-only
            STATUS current
            DESCRIPTION
                "This object indicates the number of multicast LBM packets that have been sent."
            ::= { hwY1731MulPingEntry 9 }


        hwY1731MulPingRecvPacketNum OBJECT-TYPE
            SYNTAX Counter32
            MAX-ACCESS read-only
            STATUS current
            DESCRIPTION
                "This object indicates the number of multicast LBM packets that have been received."
            ::= { hwY1731MulPingEntry 10 }


        hwY1731MulPingRecvTimeDelayMin OBJECT-TYPE
            SYNTAX Unsigned32
            MAX-ACCESS read-only
            STATUS current
            DESCRIPTION
                "This object indicates the minimum delay after which LBR packets are received."
            ::= { hwY1731MulPingEntry 11 }


        hwY1731MulPingRecvTimeDelayMax OBJECT-TYPE
            SYNTAX Unsigned32
            MAX-ACCESS read-only
            STATUS current
            DESCRIPTION
                "This object indicates the maximum delay after which LBR packets are received."
            ::= { hwY1731MulPingEntry 12 }


        hwY1731MulPingRecvTimeDelayAvg OBJECT-TYPE
            SYNTAX Unsigned32
            MAX-ACCESS read-only
            STATUS current
            DESCRIPTION
                "This object indicates the average delay after which LBR packets are received."
            ::= { hwY1731MulPingEntry 13 }


        hwY1731MulPingRowStatus OBJECT-TYPE
            SYNTAX RowStatus
            MAX-ACCESS read-create
            STATUS current
            DESCRIPTION
                "This object indicates the row status of this table.

                 The writable columns in a row can not be changed if the row
                 is active. All columns MUST have a valid value before a row
                 can be activated.
                "
            ::= { hwY1731MulPingEntry 99 }


        hwY1731MulPingReplyTable OBJECT-TYPE
            SYNTAX SEQUENCE OF HwY1731MulPingReplyEntry
            MAX-ACCESS not-accessible
            STATUS current
            DESCRIPTION
                "This table is used to display information about the multicast
                 LBRs for responding to the multicast MAC ping operation.
                "
            ::= { hwY1731ConfigObject 7 }


        hwY1731MulPingReplyEntry OBJECT-TYPE
            SYNTAX HwY1731MulPingReplyEntry
            MAX-ACCESS not-accessible
            STATUS current
            DESCRIPTION
                "The entry of multicast ping reply."
            INDEX { hwY1731MulPingReplySeqNumber, hwY1731MulPingReplyOrder }
            ::= { hwY1731MulPingReplyTable 1 }


        HwY1731MulPingReplyEntry ::=
            SEQUENCE {
                hwY1731MulPingReplySeqNumber
                    Unsigned32,
                hwY1731MulPingReplyOrder
                    Unsigned32,
                hwY1731MulPingReplyMepId
                    Integer32,
                hwY1731MulPingReplyMacAddress
                    MacAddress,
                hwY1731MulPingReplyTransTime
                    Unsigned32
             }

        hwY1731MulPingReplySeqNumber OBJECT-TYPE
            SYNTAX Unsigned32
            MAX-ACCESS not-accessible
            STATUS current
            DESCRIPTION
                "This object indicates the sequence number of the multicast LBR."
            ::= { hwY1731MulPingReplyEntry 1 }


        hwY1731MulPingReplyOrder OBJECT-TYPE
            SYNTAX Unsigned32
            MAX-ACCESS not-accessible
            STATUS current
            DESCRIPTION
                "This object indicates the order in which multicast LBRs are received."
            ::= { hwY1731MulPingReplyEntry 2 }


        hwY1731MulPingReplyMepId OBJECT-TYPE
            SYNTAX Integer32 (0 | 1..8191)
            MAX-ACCESS read-only
            STATUS current
            DESCRIPTION
                "This object indicates the MEP ID carried in the multicast LBRs.
                 The value ranges from 0 to 8191.
                 The value 0 is an invalid value.
                "
            ::= { hwY1731MulPingReplyEntry 3 }


        hwY1731MulPingReplyMacAddress OBJECT-TYPE
            SYNTAX MacAddress
            MAX-ACCESS read-only
            STATUS current
            DESCRIPTION
                "This object indicates the MAC address carried in the multicast LBRs."
            ::= { hwY1731MulPingReplyEntry 4 }


        hwY1731MulPingReplyTransTime OBJECT-TYPE
            SYNTAX Unsigned32
            MAX-ACCESS read-only
            STATUS current
            DESCRIPTION
                "This object indicates the period from the time when the multicast LBM
                 is sent to the time when the multicast LBR is received.
                "
            ::= { hwY1731MulPingReplyEntry 5 }
        
        hwY1731AisVlanConfigTable OBJECT-TYPE
            SYNTAX SEQUENCE OF HwY1731AisVlanConfigEntry
            MAX-ACCESS not-accessible
            STATUS current
            DESCRIPTION
                "This table is used to configure the information about the VLAN that
                 receives AIS frames.
                "
            ::= { hwY1731ConfigObject 8 }
        
        hwY1731AisVlanConfigEntry OBJECT-TYPE
            SYNTAX HwY1731AisVlanConfigEntry
            MAX-ACCESS not-accessible
            STATUS current
            DESCRIPTION
                "The entry of alarm indication signal about vlan infomation."
            INDEX { hwDot1agCfmMdIndex, hwDot1agCfmMaIndex, hwDot1agCfmMepIdentifier, hwY1731AisConfigPeVlan }
            ::= { hwY1731AisVlanConfigTable 1 }


        HwY1731AisVlanConfigEntry ::=
            SEQUENCE {
                hwY1731AisConfigPeVlan
                    VlanIdOrNone,
                hwY1731AisConfigVlanListLow
                    OCTET STRING,
                hwY1731AisConfigVlanListHigh
                    OCTET STRING,
                hwY1731AisVlanConfigRowStatus
                    RowStatus
             }

        hwY1731AisConfigPeVlan OBJECT-TYPE
            SYNTAX VlanIdOrNone
            MAX-ACCESS not-accessible
            STATUS current
            DESCRIPTION
                "This object indicates the ID of the PE VLAN corresponding to the AIS function.
                 The value 0 indicates that the PE VLAN is not set.
                "
            ::= { hwY1731AisVlanConfigEntry 1 }


        hwY1731AisConfigVlanListLow OBJECT-TYPE
            SYNTAX OCTET STRING (SIZE(256))
            MAX-ACCESS read-create
            STATUS current
            DESCRIPTION
                "If hwY1731AisConfigPeVlan is set to 0, the object indicates a VLAN list corresponding to the AIS function. If its value is not 0, this object indicates a CE VLAN list. The VLAN ID ranges 1 to 2047. The hwY1731AisConfigVlanListHigh value ranges 2048 to 4094. 
                "
            ::= { hwY1731AisVlanConfigEntry 2 }


        hwY1731AisConfigVlanListHigh OBJECT-TYPE
            SYNTAX OCTET STRING (SIZE(256))
            MAX-ACCESS read-create
            STATUS current
            DESCRIPTION
                "If hwY1731AisConfigPeVlan is set to 0, the object indicates a VLAN list corresponding to the AIS function. If its value is not 0, this object indicates a CE VLAN list. The VLAN ID ranges 2048 to 4094. The hwY1731AisConfigVlanListLow value ranges value 1 to 2047.
                "
            ::= { hwY1731AisVlanConfigEntry 3 }


        hwY1731AisVlanConfigRowStatus OBJECT-TYPE
            SYNTAX RowStatus
            MAX-ACCESS read-create
            STATUS current
            DESCRIPTION
                "This object indicates the row status of this table.

                 The writable columns in a row can not be changed if the row
                 is active. All columns MUST have a valid value before a row
                 can be activated."
            ::= { hwY1731AisVlanConfigEntry 4 }
        hwY1731TestIdTable OBJECT-TYPE
            SYNTAX SEQUENCE OF HwY1731TestIdEntry
            MAX-ACCESS not-accessible
            STATUS current
            DESCRIPTION
                "This table defines the information about TestId.
                "
            ::= { hwY1731ConfigObject 9 }
            
         hwY1731TestIdEntry OBJECT-TYPE
            SYNTAX HwY1731TestIdEntry
            MAX-ACCESS not-accessible
            STATUS current
            DESCRIPTION
                "The configuration entry of TestId."
            INDEX { hwY1731TestIdentifier }
            ::= { hwY1731TestIdTable 1 }


        HwY1731TestIdEntry ::=
            SEQUENCE {
                hwY1731TestIdentifier
                    Unsigned32,
                hwY1731TestIdMdName
                    OCTET STRING,
                hwY1731TestIdMaName    
                    OCTET STRING,
                hwY1731TestIdLocalMepId    
                    Integer32,
                hwY1731TestIdDestIsMepId    
                    TruthValue,
                hwY1731TestIdDestMepId    
                    Integer32,
                hwY1731TestIdDestMepMacAddress
                    MacAddress,
                hwY1731TestIdOnwardMacAddress 
                    MacAddress,
                hwY1731TestIdBackwardMacAddress 
                    MacAddress,
                hwY1731TestIdIsUpdateOnwardMacAddress     
                    TruthValue,
                hwY1731TestIdIsUpdateBackwardMacAddress    
                    TruthValue,    
                hwY1731TestId8021pValue    
                    Integer32,
                hwY1731TestIdUplink8021p    
                    Integer32,
                hwY1731TestIdDownlink8021p
                    Integer32,
                hwY1731TestIdDescription
                    OCTET STRING,
                hwY1731TestIdRowStatus
                    RowStatus
             }

        hwY1731TestIdentifier OBJECT-TYPE
            SYNTAX Unsigned32 (1..4294967295)
            MAX-ACCESS read-only
            STATUS current
            DESCRIPTION
                "This object indicates the ID of the test.
                  "
            ::= { hwY1731TestIdEntry 1 }                    

        hwY1731TestIdMdName OBJECT-TYPE
            SYNTAX OCTET STRING (SIZE (1..43))
            MAX-ACCESS read-create
            STATUS current
            DESCRIPTION
                "This object indicates the name of the MD in which TestId is configured.
                "
            ::= { hwY1731TestIdEntry 2 }
            
        hwY1731TestIdMaName OBJECT-TYPE
            SYNTAX OCTET STRING (SIZE (1..43))
            MAX-ACCESS read-create
            STATUS current
            DESCRIPTION
                "This object indicates the name of the MA in which TestId is configured.
                "
            ::= { hwY1731TestIdEntry 3 }
            
        hwY1731TestIdLocalMepId OBJECT-TYPE
            SYNTAX Integer32 (1..8191)
            MAX-ACCESS read-create
            STATUS current
            DESCRIPTION
                "This object indicates the ID of the local MEP that is specified 
                 in the TestId configuration.
                "
            ::= { hwY1731TestIdEntry 4 }
            
        hwY1731TestIdDestIsMepId OBJECT-TYPE
            SYNTAX TruthValue
            MAX-ACCESS read-create
            STATUS current
            DESCRIPTION
                "This object indicates whether the destination MAC address 
                is the specified RMEP's MAC address.
                The default value is false.
                "
            ::= { hwY1731TestIdEntry 5 }
          
        hwY1731TestIdDestMepId OBJECT-TYPE
            SYNTAX Integer32 (0 | 1..8191)
            MAX-ACCESS read-create
            STATUS current
            DESCRIPTION
                "This object indicates the ID of the remote MEP that is specified 
                 in the TestId configuration.
                 "
            ::= { hwY1731TestIdEntry 6 }  
         
         hwY1731TestIdDestMepMacAddress OBJECT-TYPE
            SYNTAX MacAddress
            MAX-ACCESS read-create
            STATUS current
            DESCRIPTION
                "This object indicates the MAC address of the remote end.
                "
            ::= { hwY1731TestIdEntry 7 }
          
         hwY1731TestIdOnwardMacAddress OBJECT-TYPE
            SYNTAX MacAddress
            MAX-ACCESS read-create
            STATUS current
            DESCRIPTION
                "This object indicates the onward MAC address.
                "
            ::= { hwY1731TestIdEntry 8 }  
         
         hwY1731TestIdBackwardMacAddress OBJECT-TYPE
            SYNTAX MacAddress
            MAX-ACCESS read-create
            STATUS current
            DESCRIPTION
                "This object indicates the backward MAC address.
                "
            ::= { hwY1731TestIdEntry 9 }   
               
         hwY1731TestIdIsUpdateOnwardMacAddress OBJECT-TYPE
            SYNTAX TruthValue
            MAX-ACCESS read-create
            STATUS current
            DESCRIPTION
                "This object indicates whether the onward MAC address is updated automatically.
                The default value is false.
                "
            ::= { hwY1731TestIdEntry 10 } 
            
         hwY1731TestIdIsUpdateBackwardMacAddress OBJECT-TYPE
            SYNTAX TruthValue
            MAX-ACCESS read-create
            STATUS current
            DESCRIPTION
                "This object indicates whether the backward MAC address is updated automatically.
                The default value is false.
                "
            ::= { hwY1731TestIdEntry 11 } 
            
        hwY1731TestId8021pValue OBJECT-TYPE
            SYNTAX Integer32 (0..7 | 255 )
            MAX-ACCESS read-create
            STATUS current
            DESCRIPTION
                "This object indicates the 802.1p priority.
                The value 255 is an invalid value.               
                "
            ::= { hwY1731TestIdEntry 12 } 
            
        hwY1731TestIdUplink8021p OBJECT-TYPE
            SYNTAX Integer32 (0..7 | 255 )
            MAX-ACCESS read-create
            STATUS current
            DESCRIPTION
                "This object indicates the 802.1p priority of uplink packets.
                The value 255 is an invalid value.                
                "
            ::= { hwY1731TestIdEntry 13 } 
            
        hwY1731TestIdDownlink8021p OBJECT-TYPE
            SYNTAX Integer32 (0..7 | 255 )
            MAX-ACCESS read-create
            STATUS current
            DESCRIPTION
                "This object indicates the 802.1p priority of downlink packets.
                The value 255 is an invalid value.          
                "
            ::= { hwY1731TestIdEntry 14 } 
            
        hwY1731TestIdDescription OBJECT-TYPE
            SYNTAX OCTET STRING (SIZE (0..63))
            MAX-ACCESS read-create
            STATUS current
            DESCRIPTION
                "This object indicates the description of TestId.
                "
            ::= { hwY1731TestIdEntry 15 }
            
        hwY1731TestIdRowStatus OBJECT-TYPE
            SYNTAX RowStatus
            MAX-ACCESS read-create
            STATUS current
            DESCRIPTION
                "This object indicates the row status of this table.

                 All columns MUST have a valid value before a row
                 can be activated.
                "
            ::= { hwY1731TestIdEntry 99 }
            
        hwY1731TestIdSingleEndedLMSendTable OBJECT-TYPE
            SYNTAX SEQUENCE OF HwY1731TestIdSingleEndedLMSendEntry
            MAX-ACCESS not-accessible
            STATUS current
            DESCRIPTION
                "This table configures the single-ended ETH-LM sending function.
                "
            ::= { hwY1731ConfigObject 10 }                     
            
         hwY1731TestIdSingleEndedLMSendEntry OBJECT-TYPE
            SYNTAX HwY1731TestIdSingleEndedLMSendEntry
            MAX-ACCESS not-accessible
            STATUS current
            DESCRIPTION
                "The configuration entry of the single-ended ETH-LM sending function."
            INDEX { hwY1731TestIdentifier }
            ::= { hwY1731TestIdSingleEndedLMSendTable 1 }

        HwY1731TestIdSingleEndedLMSendEntry ::=
            SEQUENCE {                
                hwY1731TestIdSingleEndedLMSendIsContinue
                    TruthValue,
                hwY1731TestIdSingleEndedLMSendInterval
                    INTEGER,
                hwY1731TestIdSingleEndedLMSendCount
                    Integer32,
                hwY1731TestIdSingleEndedLMSendRowStatus
                    RowStatus               
             }        

        hwY1731TestIdSingleEndedLMSendIsContinue OBJECT-TYPE
            SYNTAX TruthValue
            MAX-ACCESS read-create
            STATUS current
            DESCRIPTION
                "This object indicates whether single-ended ETH-LM sending is continual.
                 If the value is 'false', it indicates that the single-ended ETH-LM is on-demand.
                "
            ::= { hwY1731TestIdSingleEndedLMSendEntry 1 }

        hwY1731TestIdSingleEndedLMSendInterval OBJECT-TYPE
            SYNTAX INTEGER
                {
                invalid(1),
                interval1s(2),
                interval10s(3),
                interval30s(4)
                }
            MAX-ACCESS read-create
            STATUS current
            DESCRIPTION
                "This object indicates the interval at which LMM frames are sent.
                 the value can be:
                    1 second
                    10 seconds
                    30 seconds
                "
            ::= { hwY1731TestIdSingleEndedLMSendEntry 2 }

        hwY1731TestIdSingleEndedLMSendCount OBJECT-TYPE
            SYNTAX Integer32 (0 | 1..60)
            MAX-ACCESS read-create
            STATUS current
            DESCRIPTION
                "This object indicates the number of the sent LMM frames.
                 The value can be 0 or ranges from 1 to 60.
                 In a proactive OAM scenario, the value is 0."
            ::= { hwY1731TestIdSingleEndedLMSendEntry 3 }    
        
        hwY1731TestIdSingleEndedLMSendRowStatus OBJECT-TYPE
            SYNTAX RowStatus
            MAX-ACCESS read-create
            STATUS current
            DESCRIPTION
                "This object indicates the row status of this table.

                 All columns MUST have a valid value before a row
                 can be activated.
                "
            ::= { hwY1731TestIdSingleEndedLMSendEntry 99 }
            
        hwY1731TestIdSingleEndedLMReceiveTable OBJECT-TYPE
            SYNTAX SEQUENCE OF HwY1731TestIdSingleEndedLMReceiveEntry
            MAX-ACCESS not-accessible
            STATUS current
            DESCRIPTION
                "This table configures the single-ended ETH-LM receiving function.
                "
            ::= { hwY1731ConfigObject 11 }
            
        hwY1731TestIdSingleEndedLMReceiveEntry OBJECT-TYPE
            SYNTAX HwY1731TestIdSingleEndedLMReceiveEntry
            MAX-ACCESS not-accessible
            STATUS current
            DESCRIPTION
                "The configuration entry of the single-ended ETH-LM receiving function."
            INDEX { hwY1731TestIdentifier }
            ::= { hwY1731TestIdSingleEndedLMReceiveTable 1 }

        HwY1731TestIdSingleEndedLMReceiveEntry ::=
            SEQUENCE {
                hwY1731TestIdSingleEndedLMReceiveRowStatus
                    RowStatus               
             }

        hwY1731TestIdSingleEndedLMReceiveRowStatus OBJECT-TYPE
            SYNTAX RowStatus
            MAX-ACCESS read-create
            STATUS current
            DESCRIPTION
                "This object indicates the row status of this table.

                 All columns MUST have a valid value before a row
                 can be activated.
                "
            ::= { hwY1731TestIdSingleEndedLMReceiveEntry 99 }  

        hwY1731TestIdOneWayDMSendTable OBJECT-TYPE
            SYNTAX SEQUENCE OF HwY1731TestIdOneWayDMSendEntry
            MAX-ACCESS not-accessible
            STATUS current
            DESCRIPTION
                "This table configures the one-way ETH-DM sending function.
                "
            ::= { hwY1731ConfigObject 12 }
            
         hwY1731TestIdOneWayDMSendEntry OBJECT-TYPE
            SYNTAX HwY1731TestIdOneWayDMSendEntry
            MAX-ACCESS not-accessible
            STATUS current
            DESCRIPTION
                "The configuration entry of the one-way ETH-DM sending function."
            INDEX { hwY1731TestIdentifier }
            ::= { hwY1731TestIdOneWayDMSendTable 1 }

        HwY1731TestIdOneWayDMSendEntry ::=
            SEQUENCE {
                hwY1731TestIdOneWayDMSendIsContinue
                    TruthValue,
                hwY1731TestIdOneWayDMSendInterval
                    INTEGER,
                hwY1731TestIdOneWayDMSendCount
                    Integer32,
                hwY1731TestIdOneWayDMSendPacketSize 
                    Integer32,
                hwY1731TestIdOneWayDMSendRowStatus
                    RowStatus             
             }        

        hwY1731TestIdOneWayDMSendIsContinue OBJECT-TYPE
            SYNTAX TruthValue
            MAX-ACCESS read-create
            STATUS current
            DESCRIPTION
                "This object indicates whether one-way ETH-DM sending is continual.
                 If the value is 'false', it indicates that one-way ETH-DM is on-demand.
                "
            ::= { hwY1731TestIdOneWayDMSendEntry 1 }

        hwY1731TestIdOneWayDMSendInterval OBJECT-TYPE
            SYNTAX INTEGER
                {
                invalid(1),
                interval1s(2),
                interval10s(3),
                interval30s(4)
                }
            MAX-ACCESS read-create
            STATUS current
            DESCRIPTION
                "This object indicates the interval at which 1DM frames are sent.
                 the value can be:
                    1 second
                    10 seconds
                    30 seconds
                "
            ::= { hwY1731TestIdOneWayDMSendEntry 2 }

        hwY1731TestIdOneWayDMSendCount OBJECT-TYPE
            SYNTAX Integer32 (0 | 1..60)
            MAX-ACCESS read-create
            STATUS current
            DESCRIPTION
                "This object indicates the number of 1DM frames to be sent.
                 In a proactive OAM scenario, the value is 0."
            ::= { hwY1731TestIdOneWayDMSendEntry 3 }

        hwY1731TestIdOneWayDMSendPacketSize  OBJECT-TYPE
            SYNTAX Integer32 (0 | 64..1518)
            MAX-ACCESS read-create
            STATUS current
            DESCRIPTION
                "This object indicates the size of a one-way ETH-DM packet.
                 The value 0 means that the packet size is not specified.
                 By default, the value is 0.
                "
            ::= { hwY1731TestIdOneWayDMSendEntry 4 }
            
        hwY1731TestIdOneWayDMSendRowStatus OBJECT-TYPE
            SYNTAX RowStatus
            MAX-ACCESS read-create
            STATUS current
            DESCRIPTION
                "This object indicates the row status of this table.

                 All columns MUST have a valid value before a row
                 can be activated.
                "
            ::= { hwY1731TestIdOneWayDMSendEntry 99 }
        
        hwY1731TestIdOneWayDMReceiveTable OBJECT-TYPE
            SYNTAX SEQUENCE OF HwY1731TestIdOneWayDMReceiveEntry
            MAX-ACCESS not-accessible
            STATUS current
            DESCRIPTION
                "This table configures the one-way ETH-DM receiving function.
                "
            ::= { hwY1731ConfigObject 13 }
            
        hwY1731TestIdOneWayDMReceiveEntry OBJECT-TYPE
            SYNTAX HwY1731TestIdOneWayDMReceiveEntry
            MAX-ACCESS not-accessible
            STATUS current
            DESCRIPTION
                "The configuration entry of one-way ETH-DM receiving function."
            INDEX { hwY1731TestIdentifier }
            ::= { hwY1731TestIdOneWayDMReceiveTable 1 }

        HwY1731TestIdOneWayDMReceiveEntry ::=
            SEQUENCE {                        
                hwY1731TestIdOneWayDMReceiveIsContinue
                    TruthValue,
                hwY1731TestIdOneWayDMReceiveRowStatus
                    RowStatus
             }        

        hwY1731TestIdOneWayDMReceiveIsContinue OBJECT-TYPE
            SYNTAX TruthValue
            MAX-ACCESS read-create
            STATUS current
            DESCRIPTION
                "This object indicates whether one-way ETH-DM receiving is continual.
                 If the value is 'false', it indicates that one-way ETH-DM is on-demand.
                "
            ::= { hwY1731TestIdOneWayDMReceiveEntry 1 }      
            
        hwY1731TestIdOneWayDMReceiveRowStatus OBJECT-TYPE
            SYNTAX RowStatus
            MAX-ACCESS read-create
            STATUS current
            DESCRIPTION
                "This object indicates the row status of this table.

                 All columns MUST have a valid value before a row
                 can be activated.
                "
            ::= { hwY1731TestIdOneWayDMReceiveEntry 99 }  

        hwY1731TestIdTwoWayDMSendTable OBJECT-TYPE
            SYNTAX SEQUENCE OF HwY1731TestIdTwoWayDMSendEntry
            MAX-ACCESS not-accessible
            STATUS current
            DESCRIPTION
                "This table is used to configure the two-way ETH-DM sending function.
                "
            ::= { hwY1731ConfigObject 14 }
            
         hwY1731TestIdTwoWayDMSendEntry OBJECT-TYPE
            SYNTAX HwY1731TestIdTwoWayDMSendEntry
            MAX-ACCESS not-accessible
            STATUS current
            DESCRIPTION
                "The configuration entry of the two-way ETH-DM sending function."
            INDEX { hwY1731TestIdentifier }
            ::= { hwY1731TestIdTwoWayDMSendTable 1 }

        HwY1731TestIdTwoWayDMSendEntry ::=
            SEQUENCE {  
                hwY1731TestIdTwoWayDMSendIsContinue
                    TruthValue,
                hwY1731TestIdTwoWayDMSendInterval
                    INTEGER,
                hwY1731TestIdTwoWayDMSendCount
                    Integer32,
                hwY1731TestIdTwoWayDMSendPacketSize 
                    Integer32,
                hwY1731TestIdTwoWayDMSendRowStatus
                    RowStatus                
             }        

        hwY1731TestIdTwoWayDMSendIsContinue OBJECT-TYPE
            SYNTAX TruthValue
            MAX-ACCESS read-create
            STATUS current
            DESCRIPTION
                "This object indicates whether two-way ETH-DM sending is continual.
                 If the value is 'false', it indicates that two-way ETH-DM is on-demand.
                "
            ::= { hwY1731TestIdTwoWayDMSendEntry 1 }

        hwY1731TestIdTwoWayDMSendInterval OBJECT-TYPE
            SYNTAX INTEGER
                {
                invalid(1),
                interval1s(2),
                interval10s(3),
                interval30s(4)
                }
            MAX-ACCESS read-create
            STATUS current
            DESCRIPTION
                "This object indicates the interval at which DMM frames are sent.
                 When on-demand OAM, the value can be:
                    1 second
                    10 seconds
                    30 seconds
                "
            ::= { hwY1731TestIdTwoWayDMSendEntry 2 }

        hwY1731TestIdTwoWayDMSendCount OBJECT-TYPE
            SYNTAX Integer32 (0 | 1..60)
            MAX-ACCESS read-create
            STATUS current
            DESCRIPTION
                "This object indicates the number of DMM frames to be sent.
                 In a proactive OAM scenario, the value is 0."
            ::= { hwY1731TestIdTwoWayDMSendEntry 3 }

        hwY1731TestIdTwoWayDMSendPacketSize  OBJECT-TYPE
            SYNTAX Integer32 (0 | 64..1518)
            MAX-ACCESS read-create
            STATUS current
            DESCRIPTION
                "This object indicates the size of two-way ETH-DM packet.
                  The value 0 means that the packet size is not specified.
                 By default, the value is 0.
                "
            ::= { hwY1731TestIdTwoWayDMSendEntry 4 }
            
        hwY1731TestIdTwoWayDMSendRowStatus OBJECT-TYPE
            SYNTAX RowStatus
            MAX-ACCESS read-create
            STATUS current
            DESCRIPTION
                "This object indicates the row status of this table.

                 All columns MUST have a valid value before a row
                 can be activated.
                "
            ::= { hwY1731TestIdTwoWayDMSendEntry 99 }

        hwY1731TestIdTwoWayDMReceiveTable OBJECT-TYPE
            SYNTAX SEQUENCE OF HwY1731TestIdTwoWayDMReceiveEntry
            MAX-ACCESS not-accessible
            STATUS current
            DESCRIPTION
                "This table configures the two-way ETH-DM receiving function.
                "
            ::= { hwY1731ConfigObject 15 }
            
        hwY1731TestIdTwoWayDMReceiveEntry OBJECT-TYPE
            SYNTAX HwY1731TestIdTwoWayDMReceiveEntry
            MAX-ACCESS not-accessible
            STATUS current
            DESCRIPTION
                "The configuration entry of the two-way ETH-DM receiving function."
            INDEX { hwY1731TestIdentifier }
            ::= { hwY1731TestIdTwoWayDMReceiveTable 1 }

        HwY1731TestIdTwoWayDMReceiveEntry ::=
            SEQUENCE {
                hwY1731TestIdTwoWayDMReceiveRowStatus
                    RowStatus               
             }

        hwY1731TestIdTwoWayDMReceiveRowStatus OBJECT-TYPE
            SYNTAX RowStatus 
            MAX-ACCESS read-create
            STATUS current
            DESCRIPTION
                "This object indicates the row status of this table.

                 All columns MUST have a valid value before a row
                 can be activated.
                "
            ::= { hwY1731TestIdTwoWayDMReceiveEntry 99 }        

        hwY1731StatisticObject OBJECT IDENTIFIER ::= { hwEthOamY1731 2 }

        hwY1731ResetStatisticTable OBJECT-TYPE
            SYNTAX SEQUENCE OF HwY1731ResetStatisticEntry
            MAX-ACCESS not-accessible
            STATUS current
            DESCRIPTION
                "This table is used to reset statistic information.
                "
            ::= { hwY1731StatisticObject 1 }


        hwY1731ResetStatisticEntry OBJECT-TYPE
            SYNTAX HwY1731ResetStatisticEntry
            MAX-ACCESS not-accessible
            STATUS current
            DESCRIPTION
                "The entry of reset statistic information."
            INDEX {  hwDot1agCfmMdIndex, hwDot1agCfmMaIndex, hwY1731RemoteIp, hwY1731VcId, hwY1731MacAddress, hwY1731ResvIndex  }
            ::= { hwY1731ResetStatisticTable 1 }


        HwY1731ResetStatisticEntry ::=
            SEQUENCE {
                hwY1731ResetStatisticType
                    INTEGER,
                hwY1731ResetStatistic8021pValue
                    Integer32
             }

        hwY1731ResetStatisticType OBJECT-TYPE
            SYNTAX INTEGER
            {
              invalid(1),
              singleloss(2),
              dualloss(3),
              onewaydelay(4),
              twowaydelay(5)
            }
            MAX-ACCESS read-write
            STATUS current
            DESCRIPTION
                "This object indicates the type of reset.
                 The value can be:
                    invalid
                    singleloss
                    dualloss
                    onewaydelay
                    twowaydelay
                 The default value is invalid."
            ::= { hwY1731ResetStatisticEntry 1 }
            
        hwY1731ResetStatistic8021pValue OBJECT-TYPE
            SYNTAX Integer32 (0 | 1..255)
            MAX-ACCESS read-write
            STATUS current
            DESCRIPTION
                "This object indicates the priority of 802.1p which in the ResetStatistic.
                The priority value ranges from 0 to 7. It maps a 8 bits number.
                0 - 1  (0x01)
                1 - 2  (0x02)
                2 - 4  (0x04)
                3 - 8  (0x08)
                4 - 16 (0x10)
                5 - 32 (0x20)
                6 - 64 (0x40)
                7 - 128(0x80)
                For example, if 802.1p priority is 0 , 4 , 7, the value is 145(1 + 16 + 128).
                The value 0 indicates that the priority is not set.
                "
            ::= { hwY1731ResetStatisticEntry 2 }


        hwY1731StatisticTable OBJECT-TYPE
            SYNTAX      SEQUENCE OF HwY1731StatisticEntry
            MAX-ACCESS  not-accessible
            STATUS      current
            DESCRIPTION
              "This table is used to store the result about Y1731 statistic information.
              "
            ::= { hwY1731StatisticObject 2 }

        hwY1731StatisticEntry OBJECT-TYPE
            SYNTAX      HwY1731StatisticEntry
            MAX-ACCESS  not-accessible
            STATUS      current
            DESCRIPTION
              "An entry in the table, containing information on the Y1731 statistic entity."
            INDEX       { hwDot1agCfmMdIndex, hwDot1agCfmMaIndex, hwY1731RemoteIp, hwY1731VcId, hwY1731MacAddress, hwY1731ResvIndex }
            ::= { hwY1731StatisticTable 1 }

         HwY1731StatisticEntry ::=
            SEQUENCE {
              hwY1731SingleLossStatisticGatherInterval
                 INTEGER,
              hwY1731SingleLossLocalStatistic
                 OCTET STRING,
              hwY1731SingleLossLocalRatio
                 OCTET STRING,
              hwY1731SingleLossLocalRatioMax
                 Integer32,
              hwY1731SingleLossLocalRatioMin
                 Integer32,
              hwY1731SingleLossLocalRatioAvg
                 Integer32,
              hwY1731SingleLossRemoteStatistic
                 OCTET STRING,
              hwY1731SingleLossRemoteRatio
                 OCTET STRING,
              hwY1731SingleLossRemoteRatioMax
                 Integer32,
              hwY1731SingleLossRemoteRatioMin
                 Integer32,
              hwY1731SingleLossRemoteRatioAvg
                 Integer32,
              hwY1731OneDelayStatistic
                 OCTET STRING,
              hwY1731OneDelayVariation
                 OCTET STRING,
              hwY1731OneDelayMax
                 Unsigned32,
              hwY1731OneDelayMin
                 Unsigned32,
              hwY1731OneDelayAvg
                 Unsigned32,
              hwY1731TwoDelayStatistic
                 OCTET STRING,
              hwY1731TwoDelayVariation
                 OCTET STRING,
              hwY1731TwoDelayMax
                 Unsigned32,
              hwY1731TwoDelayMin
                 Unsigned32,
              hwY1731TwoDelayAvg
                 Unsigned32,
              hwY1731SingleLossLocalMax
                 Unsigned32,
              hwY1731SingleLossLocalMin
                 Unsigned32,
              hwY1731SingleLossLocalAvg
                 Unsigned32,
              hwY1731SingleLossRemoteMax
                 Unsigned32,
              hwY1731SingleLossRemoteMin
                 Unsigned32,
              hwY1731SingleLossRemoteAvg
                 Unsigned32,
              hwY1731OneDelayStatisticMax
                 Integer32,
              hwY1731OneDelayStatisticMin
                 Integer32,
              hwY1731OneDelayStatisticAvg
                 Integer32,              
              hwY1731TwoDelayStatisticMax
                 Unsigned32,
              hwY1731TwoDelayStatisticMin
                 Unsigned32,
              hwY1731TwoDelayStatisticAvg
                 Unsigned32,
              hwY1731TwoDelayUnresponsivePacketCount
                 Unsigned32,
              hwY1731SingleLossStatistic8021pValue
                 Integer32,
              hwY1731OneDelayStatistic8021pValue
                 Integer32,
              hwY1731TwoDelayStatistic8021pValue
                 Integer32
            }

        hwY1731SingleLossStatisticGatherInterval OBJECT-TYPE
            SYNTAX INTEGER
            {
              invalid(1),
              interval1000ms(2),
              interval10000ms(3),
              interval30000ms(4)
            }
            MAX-ACCESS read-only
            STATUS current
            DESCRIPTION
                "This object identifies an interval for collecting packet loss statistics."
            ::= { hwY1731StatisticEntry 1 }

         hwY1731SingleLossLocalStatistic OBJECT-TYPE
            SYNTAX OCTET STRING (SIZE(0..1024))
            MAX-ACCESS read-only
            STATUS current
            DESCRIPTION
                "This object identifies the packet loss statistics that are collected on a local end."
            ::= { hwY1731StatisticEntry 2 }

         hwY1731SingleLossLocalRatio OBJECT-TYPE
            SYNTAX OCTET STRING (SIZE(0..1024))
            MAX-ACCESS read-only
            STATUS current
            DESCRIPTION
                "This object identifies the packet loss ratio that are collected on a local end."
            ::= { hwY1731StatisticEntry 3 }

         hwY1731SingleLossLocalRatioMax OBJECT-TYPE
            SYNTAX Integer32
            MAX-ACCESS read-only
            STATUS current
            DESCRIPTION
                "This object identifies the maximum value of packet loss ratio 
                 that are collected on a local end."
            ::= { hwY1731StatisticEntry 4 }

         hwY1731SingleLossLocalRatioMin OBJECT-TYPE
            SYNTAX Integer32
            MAX-ACCESS read-only
            STATUS current
            DESCRIPTION
                "This object identifies the minimum value of packet loss ratio 
                 that are collected on a local end."
            ::= { hwY1731StatisticEntry 5 }

         hwY1731SingleLossLocalRatioAvg OBJECT-TYPE
            SYNTAX Integer32
            MAX-ACCESS read-only
            STATUS current
            DESCRIPTION
                "This object identifies the average value of packet loss ratio 
                 that are collected on a local end."
            ::= { hwY1731StatisticEntry 6 }

         hwY1731SingleLossRemoteStatistic OBJECT-TYPE
            SYNTAX OCTET STRING (SIZE(0..1024))
            MAX-ACCESS read-only
            STATUS current
            DESCRIPTION
                "This object identifies the packet loss statistics that are collected on a remote end."
            ::= { hwY1731StatisticEntry 7 }

         hwY1731SingleLossRemoteRatio OBJECT-TYPE
            SYNTAX OCTET STRING (SIZE(0..1024))
            MAX-ACCESS read-only
            STATUS current
            DESCRIPTION
                "This object identifies the packet loss ratio that are collected on a remote end."
            ::= { hwY1731StatisticEntry 8 }

         hwY1731SingleLossRemoteRatioMax OBJECT-TYPE
            SYNTAX Integer32
            MAX-ACCESS read-only
            STATUS current
            DESCRIPTION
                "This object identifies the maximum value of packet loss ratio 
                 that are collected on a remote end."
            ::= { hwY1731StatisticEntry 9 }

         hwY1731SingleLossRemoteRatioMin OBJECT-TYPE
            SYNTAX Integer32
            MAX-ACCESS read-only
            STATUS current
            DESCRIPTION
                "This object identifies the minimum value of packet loss ratio 
                 that are collected on a remote end."
            ::= { hwY1731StatisticEntry 10 }

         hwY1731SingleLossRemoteRatioAvg OBJECT-TYPE
            SYNTAX Integer32
            MAX-ACCESS read-only
            STATUS current
            DESCRIPTION
                "This object identifies the average value of packet loss ratio 
                 that are collected on a remote end."
            ::= { hwY1731StatisticEntry 11 }

        hwY1731OneDelayStatistic OBJECT-TYPE
            SYNTAX OCTET STRING (SIZE (0..1024))
            MAX-ACCESS  read-only
            STATUS      current
            DESCRIPTION
              "This object indicates the statistics about the one-way delay."
            ::= { hwY1731StatisticEntry 12 }

        hwY1731OneDelayVariation OBJECT-TYPE
            SYNTAX OCTET STRING (SIZE (0..1024))
            MAX-ACCESS  read-only
            STATUS      current
            DESCRIPTION
              "This object indicates the variation about the one-way delay.
               After the device is enabled to receive packets, statistics collected for the first time are invalid, and the value of hwY1731OneDelayVariation is setted to 0.
              "
            ::= { hwY1731StatisticEntry 13 }

         hwY1731OneDelayMax OBJECT-TYPE
            SYNTAX Unsigned32
            MAX-ACCESS read-only
            STATUS current
            DESCRIPTION
                "This object identifies the maximum variation of the one-way delay."
            ::= { hwY1731StatisticEntry 14 }

         hwY1731OneDelayMin OBJECT-TYPE
            SYNTAX Unsigned32
            MAX-ACCESS read-only
            STATUS current
            DESCRIPTION
                "This object identifies the minimum variation of the one-way delay."
            ::= { hwY1731StatisticEntry 15 }

         hwY1731OneDelayAvg OBJECT-TYPE
            SYNTAX Unsigned32
            MAX-ACCESS read-only
            STATUS current
            DESCRIPTION
                "This object identifies the average variation of the one-way delay."
            ::= { hwY1731StatisticEntry 16 }

        hwY1731TwoDelayStatistic OBJECT-TYPE
            SYNTAX OCTET STRING (SIZE (0..1024))
            MAX-ACCESS  read-only
            STATUS      current
            DESCRIPTION
              "This object indicates the statistics about the two-way delay."
            ::= { hwY1731StatisticEntry 17 }

        hwY1731TwoDelayVariation OBJECT-TYPE
            SYNTAX OCTET STRING (SIZE (0..1024))
            MAX-ACCESS  read-only
            STATUS      current
            DESCRIPTION
              "This object indicates the variation about the two-way delay."
            ::= { hwY1731StatisticEntry 18 }

         hwY1731TwoDelayMax OBJECT-TYPE
            SYNTAX Unsigned32
            MAX-ACCESS read-only
            STATUS current
            DESCRIPTION
                "This object identifies the maximum variation of the two-way delay."
            ::= { hwY1731StatisticEntry 19 }

         hwY1731TwoDelayMin OBJECT-TYPE
            SYNTAX Unsigned32
            MAX-ACCESS read-only
            STATUS current
            DESCRIPTION
                "This object identifies the minimum variation of the two-way delay."
            ::= { hwY1731StatisticEntry 20 }

         hwY1731TwoDelayAvg OBJECT-TYPE
            SYNTAX Unsigned32
            MAX-ACCESS read-only
            STATUS current
            DESCRIPTION
                "This object identifies the average variation of the two-way delay."
            ::= { hwY1731StatisticEntry 21 }
            
         
         hwY1731SingleLossLocalMax OBJECT-TYPE
            SYNTAX Unsigned32
            MAX-ACCESS read-only
            STATUS current
            DESCRIPTION
                "This object identifies the maximum value of packet loss 
                 that are collected on a local end."
            ::= { hwY1731StatisticEntry 22 }

         hwY1731SingleLossLocalMin OBJECT-TYPE
            SYNTAX Unsigned32
            MAX-ACCESS read-only
            STATUS current
            DESCRIPTION
                "This object identifies the minimum value of packet loss  
                 that are collected on a local end."
            ::= { hwY1731StatisticEntry 23 }

         hwY1731SingleLossLocalAvg OBJECT-TYPE
            SYNTAX Unsigned32
            MAX-ACCESS read-only
            STATUS current
            DESCRIPTION
                "This object identifies the average value of packet loss 
                 that are collected on a local end."
            ::= { hwY1731StatisticEntry 24 }
            
         hwY1731SingleLossRemoteMax OBJECT-TYPE
            SYNTAX Unsigned32
            MAX-ACCESS read-only
            STATUS current
            DESCRIPTION
                "This object identifies the maximum value of packet loss 
                 that are collected on a remote end."
            ::= { hwY1731StatisticEntry 25 }

         hwY1731SingleLossRemoteMin OBJECT-TYPE
            SYNTAX Unsigned32
            MAX-ACCESS read-only
            STATUS current
            DESCRIPTION
                "This object identifies the minimum value of packet loss 
                 that are collected on a remote end."
            ::= { hwY1731StatisticEntry 26 }

         hwY1731SingleLossRemoteAvg OBJECT-TYPE
            SYNTAX Unsigned32
            MAX-ACCESS read-only
            STATUS current
            DESCRIPTION
                "This object identifies the average value of packet loss 
                 that are collected on a remote end."
            ::= { hwY1731StatisticEntry 27 }
            
         hwY1731OneDelayStatisticMax OBJECT-TYPE
            SYNTAX Integer32
            MAX-ACCESS read-only
            STATUS current
            DESCRIPTION
                "This object identifies the maximum value of the one-way delay."
            ::= { hwY1731StatisticEntry 28 }

         hwY1731OneDelayStatisticMin OBJECT-TYPE
            SYNTAX Integer32
            MAX-ACCESS read-only
            STATUS current
            DESCRIPTION
                "This object identifies the minimum value of the one-way delay."
            ::= { hwY1731StatisticEntry 29 }

         hwY1731OneDelayStatisticAvg OBJECT-TYPE
            SYNTAX Integer32
            MAX-ACCESS read-only
            STATUS current
            DESCRIPTION
                "This object identifies the average value of the one-way delay."
            ::= { hwY1731StatisticEntry 30 }
        
         hwY1731TwoDelayStatisticMax OBJECT-TYPE
            SYNTAX Unsigned32
            MAX-ACCESS read-only
            STATUS current
            DESCRIPTION
                "This object identifies the maximum value of the two-way delay."
            ::= { hwY1731StatisticEntry 31 }

         hwY1731TwoDelayStatisticMin OBJECT-TYPE
            SYNTAX Unsigned32
            MAX-ACCESS read-only
            STATUS current
            DESCRIPTION
                "This object identifies the minimum value of the two-way delay."
            ::= { hwY1731StatisticEntry 32 }

         hwY1731TwoDelayStatisticAvg OBJECT-TYPE
            SYNTAX Unsigned32
            MAX-ACCESS read-only
            STATUS current
            DESCRIPTION
                "This object identifies the average value of the two-way delay."
            ::= { hwY1731StatisticEntry 33 }   
        
         hwY1731TwoDelayUnresponsivePacketCount OBJECT-TYPE
            SYNTAX Unsigned32
            MAX-ACCESS read-only
            STATUS current
            DESCRIPTION
                "This object identifies the number of unresponsive Delay Measurement Reply frames."
            ::= { hwY1731StatisticEntry 34 }

         hwY1731SingleLossStatistic8021pValue OBJECT-TYPE
            SYNTAX Integer32 (0..7 | 255 )
            MAX-ACCESS read-only
            STATUS current
            DESCRIPTION
                "This object indicates the 802.1p priority.
                The value 255 is an invalid value.
                "
            ::= { hwY1731StatisticEntry 35 }

         hwY1731OneDelayStatistic8021pValue OBJECT-TYPE
            SYNTAX Integer32 (0..7 | 255 )
            MAX-ACCESS read-only
            STATUS current
            DESCRIPTION
                "This object indicates the 802.1p priority.
                The value 255 is an invalid value.
                "
            ::= { hwY1731StatisticEntry 36 }

         hwY1731TwoDelayStatistic8021pValue OBJECT-TYPE
            SYNTAX Integer32 (0..7 | 255 )
            MAX-ACCESS read-only
            STATUS current
            DESCRIPTION
                "This object indicates the 802.1p priority.
                The value 255 is an invalid value.
                "
            ::= { hwY1731StatisticEntry 37 }

         hwCfmVlanOneDelayTrapLogTable OBJECT-TYPE
            SYNTAX SEQUENCE OF HwCfmVlanOneDelayTrapLogEntry
            MAX-ACCESS not-accessible
            STATUS current
            DESCRIPTION
                "This table is used to query whether the one-way delay exceeds 
                 the trap threshold in the VLAN scenario."
            ::= { hwY1731StatisticObject 3 }

        hwCfmVlanOneDelayTrapLogEntry OBJECT-TYPE
            SYNTAX HwCfmVlanOneDelayTrapLogEntry
            MAX-ACCESS not-accessible
            STATUS current
            DESCRIPTION
                "
                An entry in the table, containing information on the trap entity.
                "
            INDEX { hwDot1agCfmMdIndex , hwDot1agCfmMaIndex  }
            ::= { hwCfmVlanOneDelayTrapLogTable 1 }

        HwCfmVlanOneDelayTrapLogEntry ::=
            SEQUENCE {
                hwCfmOneDelayTrapLogMacAddress
                    MacAddress,
                hwCfmVlanOneDelayTrapLogTimestamp
                    TimeStamp,
                hwCfmVlanOneDelayTrapLogDelayValue
                    Unsigned32,
                hwCfmVlanOneDelayTrapLogThreshold
                    Unsigned32,
                hwCfmVlanOneDelayTrapLogDelayValueHigh
                    Unsigned32,
                hwCfmVlanOneDelayTrapLogDelayValueLow
                    Unsigned32
             }

       hwCfmOneDelayTrapLogMacAddress OBJECT-TYPE
            SYNTAX MacAddress
            MAX-ACCESS accessible-for-notify
            STATUS current
            DESCRIPTION
                "
                This object indicates the remote MAC address.
                "
            ::= { hwCfmVlanOneDelayTrapLogEntry 1 }

        hwCfmVlanOneDelayTrapLogTimestamp OBJECT-TYPE
            SYNTAX TimeStamp
            MAX-ACCESS accessible-for-notify
            STATUS current
            DESCRIPTION
                "
                This object indicates the timestamp when the delay of the one-way ETH-DM 
                in the VLAN is higher than the configured trap threshold.
                "
            ::= { hwCfmVlanOneDelayTrapLogEntry 2 }

        hwCfmVlanOneDelayTrapLogDelayValue OBJECT-TYPE
            SYNTAX Unsigned32
            MAX-ACCESS accessible-for-notify
            STATUS current
            DESCRIPTION
                "
                This object indicates the delay value when the delay of the one-way ETH-DM 
                in the VLAN is higher than the configured trap threshold.
                "
            ::= { hwCfmVlanOneDelayTrapLogEntry 3 }

        hwCfmVlanOneDelayTrapLogThreshold OBJECT-TYPE
            SYNTAX Unsigned32
            MAX-ACCESS accessible-for-notify
            STATUS current
            DESCRIPTION
                "
                This object indicates the delay trap threshold of the one-way ETH-DM.
                "
            ::= { hwCfmVlanOneDelayTrapLogEntry 4 }

        hwCfmVlanOneDelayTrapLogDelayValueHigh OBJECT-TYPE
            SYNTAX Unsigned32
            MAX-ACCESS accessible-for-notify
            STATUS current
            DESCRIPTION
                "
                This object indicates the high 32 bits delay value when the delay of the one-way ETH-DM 
                in the VLAN is higher than the configured trap threshold.
                "
            ::= { hwCfmVlanOneDelayTrapLogEntry 5 }

        hwCfmVlanOneDelayTrapLogDelayValueLow OBJECT-TYPE
            SYNTAX Unsigned32
            MAX-ACCESS accessible-for-notify
            STATUS current
            DESCRIPTION
                "
                This object indicates the low 32 bits delay value when the delay of the one-way ETH-DM 
                in the VLAN is higher than the configured trap threshold.
                "
            ::= { hwCfmVlanOneDelayTrapLogEntry 6 }

        hwCfmVlanOneDelayRcoverTrapLogTable OBJECT-TYPE
            SYNTAX SEQUENCE OF HwCfmVlanOneDelayRcoverTrapLogEntry
            MAX-ACCESS not-accessible
            STATUS current
            DESCRIPTION
                "This table is used to query whether the one-way delay falls below 
                 the trap threshold."
            ::= { hwY1731StatisticObject 4 }

        hwCfmVlanOneDelayRcoverTrapLogEntry OBJECT-TYPE
            SYNTAX HwCfmVlanOneDelayRcoverTrapLogEntry
            MAX-ACCESS not-accessible
            STATUS current
            DESCRIPTION
                "
                An entry in the table, containing information on the recovery trap entity.
                "
            INDEX { hwDot1agCfmMdIndex , hwDot1agCfmMaIndex  }
            ::= { hwCfmVlanOneDelayRcoverTrapLogTable 1 }

        HwCfmVlanOneDelayRcoverTrapLogEntry ::=
            SEQUENCE {
                hwCfmOneDelayRecoveryTrapMacAddress
                    MacAddress,
                hwCfmVlanOneDelayRecoveryTrapLogTimestamp
                    TimeStamp,
                hwCfmVlanOneDelayRecoveryTrapLogDelayValue
                    Unsigned32,
                hwCfmVlanOneDelayRecoveryTrapLogThreshold
                    Unsigned32,
                hwCfmVlanOneDelayRecoveryTrapLogDelayValueHigh
                    Unsigned32,
                hwCfmVlanOneDelayRecoveryTrapLogDelayValueLow
                    Unsigned32
             }

       hwCfmOneDelayRecoveryTrapMacAddress OBJECT-TYPE
            SYNTAX MacAddress
            MAX-ACCESS accessible-for-notify
            STATUS current
            DESCRIPTION
                "
                This object indicates the remote MAC address.
                "
            ::= { hwCfmVlanOneDelayRcoverTrapLogEntry 1 }

        hwCfmVlanOneDelayRecoveryTrapLogTimestamp OBJECT-TYPE
            SYNTAX TimeStamp
            MAX-ACCESS accessible-for-notify
            STATUS current
            DESCRIPTION
                "
                This object indicates the timestamp when the delay of the one-way ETH-DM 
                in the VLAN is lower than the configured trap threshold.
                "
            ::= { hwCfmVlanOneDelayRcoverTrapLogEntry 2 }

        hwCfmVlanOneDelayRecoveryTrapLogDelayValue OBJECT-TYPE
            SYNTAX Unsigned32
            MAX-ACCESS accessible-for-notify
            STATUS current
            DESCRIPTION
                "
                This object indicates the delay value when the delay of the one-way ETH-DM 
                in the VLAN is lower than the configured trap threshold.
                "
            ::= { hwCfmVlanOneDelayRcoverTrapLogEntry 3 }

        hwCfmVlanOneDelayRecoveryTrapLogThreshold OBJECT-TYPE
            SYNTAX Unsigned32
            MAX-ACCESS accessible-for-notify
            STATUS current
            DESCRIPTION
                "
                This object indicates the delay trap threshold of the one-way ETH-DM.
                "
            ::= { hwCfmVlanOneDelayRcoverTrapLogEntry 4 }

        hwCfmVlanOneDelayRecoveryTrapLogDelayValueHigh OBJECT-TYPE
            SYNTAX Unsigned32
            MAX-ACCESS accessible-for-notify
            STATUS current
            DESCRIPTION
                "
                This object indicates the high 32 bits delay value when the delay of the one-way ETH-DM 
                in the VLAN is lower than the configured trap threshold.
                "
            ::= { hwCfmVlanOneDelayRcoverTrapLogEntry 5 }

        hwCfmVlanOneDelayRecoveryTrapLogDelayValueLow OBJECT-TYPE
            SYNTAX Unsigned32
            MAX-ACCESS accessible-for-notify
            STATUS current
            DESCRIPTION
                "
                This object indicates the low 32 bits delay value when the delay of the one-way ETH-DM 
                in the VLAN is lower than the configured trap threshold.
                "
            ::= { hwCfmVlanOneDelayRcoverTrapLogEntry 6 }
			
        hwCfmVlanTwoDelayTrapLogTable OBJECT-TYPE
            SYNTAX SEQUENCE OF HwCfmVlanTwoDelayTrapLogEntry
            MAX-ACCESS not-accessible
            STATUS current
            DESCRIPTION
                "This table is used to query whether the two-way delay exceeds 
                 the trap threshold in the VLAN scenario."
            ::= { hwY1731StatisticObject 5 }

        hwCfmVlanTwoDelayTrapLogEntry OBJECT-TYPE
            SYNTAX HwCfmVlanTwoDelayTrapLogEntry
            MAX-ACCESS not-accessible
            STATUS current
            DESCRIPTION
                "
                An entry in the table, containing information on the trap entity.
                "
            INDEX { hwDot1agCfmMdIndex , hwDot1agCfmMaIndex  }
            ::= { hwCfmVlanTwoDelayTrapLogTable 1 }

        HwCfmVlanTwoDelayTrapLogEntry ::=
            SEQUENCE {
                hwCfmTwoDelayTrapMacAddress
                    MacAddress,
                hwCfmVlanTwoDelayTrapLogTimestamp
                    TimeStamp,
                hwCfmVlanTwoDelayTrapLogDelayValue
                    Unsigned32,
                hwCfmVlanTwoDelayTrapLogThreshold
                    Unsigned32,
                hwCfmVlanTwoDelayTrapLogDelayValueHigh
                    Unsigned32,
                hwCfmVlanTwoDelayTrapLogDelayValueLow
                    Unsigned32
             }

       hwCfmTwoDelayTrapMacAddress OBJECT-TYPE
            SYNTAX MacAddress
            MAX-ACCESS accessible-for-notify
            STATUS current
            DESCRIPTION
                "
                This object indicates the remote MAC address.
                "
            ::= { hwCfmVlanTwoDelayTrapLogEntry 1 }

        hwCfmVlanTwoDelayTrapLogTimestamp OBJECT-TYPE
            SYNTAX TimeStamp
            MAX-ACCESS accessible-for-notify
            STATUS current
            DESCRIPTION
                "
                This object indicates the timestamp when the delay of the two-way ETH-DM 
                in the VLAN is higher than the configured trap threshold.
                "
            ::= { hwCfmVlanTwoDelayTrapLogEntry 2 }

        hwCfmVlanTwoDelayTrapLogDelayValue OBJECT-TYPE
            SYNTAX Unsigned32
            MAX-ACCESS accessible-for-notify
            STATUS current
            DESCRIPTION
                "
                This object indicates the delay value when the delay of the two-way ETH-DM 
                in the VLAN is higher than the configured trap threshold.
                "
            ::= { hwCfmVlanTwoDelayTrapLogEntry 3 }

        hwCfmVlanTwoDelayTrapLogThreshold OBJECT-TYPE
            SYNTAX Unsigned32
            MAX-ACCESS accessible-for-notify
            STATUS current
            DESCRIPTION
                "
                This object indicates the delay trap threshold of the two-way ETH-DM.
                "
            ::= { hwCfmVlanTwoDelayTrapLogEntry 4 }

        hwCfmVlanTwoDelayTrapLogDelayValueHigh OBJECT-TYPE
            SYNTAX Unsigned32
            MAX-ACCESS accessible-for-notify
            STATUS current
            DESCRIPTION
                "
                This object indicates the high 32 bits delay value when the delay of the two-way ETH-DM 
                in the VLAN is higher than the configured trap threshold.
                "
            ::= { hwCfmVlanTwoDelayTrapLogEntry 5 }

        hwCfmVlanTwoDelayTrapLogDelayValueLow OBJECT-TYPE
            SYNTAX Unsigned32
            MAX-ACCESS accessible-for-notify
            STATUS current
            DESCRIPTION
                "
                This object indicates the low 32 bits delay value when the delay of the two-way ETH-DM 
                in the VLAN is higher than the configured trap threshold.
                "
            ::= { hwCfmVlanTwoDelayTrapLogEntry 6 }
			
        hwCfmVlanTwoDelayRcoverTrapLogTable OBJECT-TYPE
            SYNTAX SEQUENCE OF HwCfmVlanTwoDelayRcoverTrapLogEntry
            MAX-ACCESS not-accessible
            STATUS current
            DESCRIPTION
                "This table is used to query whether the two-way delay falls below 
                 the trap threshold."
            ::= { hwY1731StatisticObject 6 }

        hwCfmVlanTwoDelayRcoverTrapLogEntry OBJECT-TYPE
            SYNTAX HwCfmVlanTwoDelayRcoverTrapLogEntry
            MAX-ACCESS not-accessible
            STATUS current
            DESCRIPTION
                "
                An entry in the table, containing information on the recovery trap entity.
                "
            INDEX { hwDot1agCfmMdIndex , hwDot1agCfmMaIndex  }
            ::= { hwCfmVlanTwoDelayRcoverTrapLogTable 1 }

        HwCfmVlanTwoDelayRcoverTrapLogEntry ::=
            SEQUENCE {
                hwCfmTwoDelayRecoveryTrapMacAddress
                    MacAddress,
                hwCfmVlanTwoDelayRecoveryTrapLogTimestamp
                    TimeStamp,
                hwCfmVlanTwoDelayRecoveryTrapLogDelayValue
                    Unsigned32,
                hwCfmVlanTwoDelayRecoveryTrapLogThreshold
                    Unsigned32,
                hwCfmVlanTwoDelayRecoveryTrapLogDelayValueHigh
                    Unsigned32,
                hwCfmVlanTwoDelayRecoveryTrapLogDelayValueLow
                    Unsigned32
             }

       hwCfmTwoDelayRecoveryTrapMacAddress OBJECT-TYPE
            SYNTAX MacAddress
            MAX-ACCESS accessible-for-notify
            STATUS current
            DESCRIPTION
                "
                This object indicates the remote MAC address.
                "
            ::= { hwCfmVlanTwoDelayRcoverTrapLogEntry 1 }

        hwCfmVlanTwoDelayRecoveryTrapLogTimestamp OBJECT-TYPE
            SYNTAX TimeStamp
            MAX-ACCESS accessible-for-notify
            STATUS current
            DESCRIPTION
                "
                This object indicates the timestamp when the delay of the two-way ETH-DM 
                in the VLAN is lower than the configured trap threshold.
                "
            ::= { hwCfmVlanTwoDelayRcoverTrapLogEntry 2 }

        hwCfmVlanTwoDelayRecoveryTrapLogDelayValue OBJECT-TYPE
            SYNTAX Unsigned32
            MAX-ACCESS accessible-for-notify
            STATUS current
            DESCRIPTION
                "
                This object indicates the delay value when the delay of the two-way ETH-DM 
                in the VLAN is lower than the configured trap threshold.
                "
            ::= { hwCfmVlanTwoDelayRcoverTrapLogEntry 3 }

        hwCfmVlanTwoDelayRecoveryTrapLogThreshold OBJECT-TYPE
            SYNTAX Unsigned32
            MAX-ACCESS accessible-for-notify
            STATUS current
            DESCRIPTION
                "
                This object indicates the delay trap threshold for the two-way ETH-DM.
                "
            ::= { hwCfmVlanTwoDelayRcoverTrapLogEntry 4 }

        hwCfmVlanTwoDelayRecoveryTrapLogDelayValueHigh OBJECT-TYPE
            SYNTAX Unsigned32
            MAX-ACCESS accessible-for-notify
            STATUS current
            DESCRIPTION
                "
                This object indicates the high 32 bits delay value when the delay of the two-way ETH-DM 
                in the VLAN is lower than the configured trap threshold.
                "
            ::= { hwCfmVlanTwoDelayRcoverTrapLogEntry 5 }

        hwCfmVlanTwoDelayRecoveryTrapLogDelayValueLow OBJECT-TYPE
            SYNTAX Unsigned32
            MAX-ACCESS accessible-for-notify
            STATUS current
            DESCRIPTION
                "
                This object indicates the low 32 bits delay value when the delay of the two-way ETH-DM 
                in the VLAN is lower than the configured trap threshold.
                "
            ::= { hwCfmVlanTwoDelayRcoverTrapLogEntry 6 }
			
        hwY1731StatisticTrapLogTable OBJECT-TYPE
            SYNTAX SEQUENCE OF HwY1731StatisticTrapLogEntry
            MAX-ACCESS not-accessible
            STATUS current
            DESCRIPTION
                "This table is used to query whether the Y.1731 statistic value triggers alarm."
            ::= { hwY1731StatisticObject 7 }

        hwY1731StatisticTrapLogEntry OBJECT-TYPE
            SYNTAX HwY1731StatisticTrapLogEntry
            MAX-ACCESS not-accessible
            STATUS current
            DESCRIPTION
                "
                An entry in the table, containing information on the statistic trap entity.
                "
            INDEX { hwDot1agCfmMdIndex , hwDot1agCfmMaIndex , hwDot1agCfmMepIdentifier , hwY1731StatisticTrapLogType , 
                    hwY1731StatisticTrapLogMacAddress , hwY1731StatisticTrapLog8021pPriority  }
            ::= { hwY1731StatisticTrapLogTable 1 }

        HwY1731StatisticTrapLogEntry ::=
            SEQUENCE {
                hwY1731StatisticTrapLogType
                    INTEGER,
                hwY1731StatisticTrapLogMacAddress
                    MacAddress, 
                hwY1731StatisticTrapLog8021pPriority
                    Integer32,
                hwY1731StatisticTrapLogValue
                    Unsigned32,
                hwY1731StatisticTrapLogUpperLimitThreshold
                    Unsigned32,
                hwY1731StatisticTrapLogLowerLimitThreshold
                    Unsigned32,
                hwY1731StatisticTrapLogValueHigh
                    Unsigned32,
                hwY1731StatisticTrapLogValueLow
                    Unsigned32
             }

        hwY1731StatisticTrapLogType OBJECT-TYPE                                    
            SYNTAX INTEGER                                            
                {                                                 
                  onedelay(1),
                  twodelay(2),
                  onedelayvariation(3),
                  twedelayvariation(4),
                  singlelosslocalratio(5),
                  singlelossremoteratio(6),
                  duallosslocalratio(7),
                  duallossremoteratio(8)
                }
            MAX-ACCESS accessible-for-notify                          
            STATUS current                                            
            DESCRIPTION                                               
                "
                Specific trap type.
                Options:                         
                1. OneDelay(1)              -indicates the trap type is delay of one-way ETH-DM.
                2. TwoDelay(2)              -indicates the trap type is delay of two-way ETH-DM.
                3. OneDelayVariation(3)     -indicates the trap type is delay variation of one-way ETH-DM.
                4. TweDelayVariation(4)     -indicates the trap type is delay variation of two-way ETH-DM.
                5. SingleLossLocalRatio(5)  -indicates the trap type is local loss ratio of single-ended ETH-LM.
                6. SingleLossRemoteRatio(6) -indicates the trap type is remote loss ratio of single-ended ETH-LM.
                7. DualLossLocalRatio(7)    -indicates the trap type is local loss ratio of dual-ended ETH-LM.
                8. DualLossRemoteRatio(8)   -indicates the trap type is remote loss ratio of dual-ended ETH-LM. 
                "                            
            ::= { hwY1731StatisticTrapLogEntry 1} 
            
        hwY1731StatisticTrapLogMacAddress OBJECT-TYPE
            SYNTAX MacAddress
            MAX-ACCESS accessible-for-notify
            STATUS current
            DESCRIPTION
                "This object indicates the remote MAC address."
            ::= { hwY1731StatisticTrapLogEntry 2 }
            
        hwY1731StatisticTrapLog8021pPriority OBJECT-TYPE
            SYNTAX Integer32
            MAX-ACCESS accessible-for-notify
            STATUS current
            DESCRIPTION
                "This object indicates the priority.
                 The value can be 255 or ranges from 0 to 7.
                 The value 255 is an invalid value.
                "
            ::= { hwY1731StatisticTrapLogEntry 3 }
            
        hwY1731StatisticTrapLogValue OBJECT-TYPE
            SYNTAX Unsigned32    
            MAX-ACCESS accessible-for-notify
            STATUS current
            DESCRIPTION
                "The value that cause the trap."
            ::= { hwY1731StatisticTrapLogEntry 4 } 
            
        hwY1731StatisticTrapLogUpperLimitThreshold OBJECT-TYPE
            SYNTAX Unsigned32    
            MAX-ACCESS accessible-for-notify
            STATUS current
            DESCRIPTION
                "The upper limit value of the threshold."
            ::= { hwY1731StatisticTrapLogEntry 5 } 
            
        hwY1731StatisticTrapLogLowerLimitThreshold OBJECT-TYPE
            SYNTAX Unsigned32    
            MAX-ACCESS accessible-for-notify
            STATUS current
            DESCRIPTION
                "The lower limit value of the threshold."
            ::= { hwY1731StatisticTrapLogEntry 6 }

        hwY1731StatisticTrapLogValueHigh OBJECT-TYPE
            SYNTAX Unsigned32    
            MAX-ACCESS accessible-for-notify
            STATUS current
            DESCRIPTION
                "The value that cause the trap."
            ::= { hwY1731StatisticTrapLogEntry 7 } 

        hwY1731StatisticTrapLogValueLow OBJECT-TYPE
            SYNTAX Unsigned32    
            MAX-ACCESS accessible-for-notify
            STATUS current
            DESCRIPTION
                "The value that cause the trap."
            ::= { hwY1731StatisticTrapLogEntry 8 } 			

        hwY1731TestIdSingleLossStatTable OBJECT-TYPE
            SYNTAX SEQUENCE OF HwY1731TestIdSingleLossStatEntry
            MAX-ACCESS not-accessible
            STATUS current
            DESCRIPTION
                "This table stores the result of single-ended ETH-LM.
                "
            ::= { hwY1731StatisticObject 8 }
            
        hwY1731TestIdSingleLossStatEntry OBJECT-TYPE
            SYNTAX HwY1731TestIdSingleLossStatEntry
            MAX-ACCESS not-accessible
            STATUS current
            DESCRIPTION
                "An entry in the table, containing information about the result of single-ended ETH-LM."
            INDEX { hwY1731TestIdentifier, hwY1731TestIdSingleLossSequence }
            ::= { hwY1731TestIdSingleLossStatTable 1 }

        HwY1731TestIdSingleLossStatEntry ::=
            SEQUENCE {
                hwY1731TestIdSingleLossSequence
                    Unsigned32,  
                hwY1731TestIdSingleLossErrInfo
                    Unsigned32,          
                hwY1731TestIdSingleLossLocal
                    Counter64,
                hwY1731TestIdSingleLossLocalRatio
                    Unsigned32,
                hwY1731TestIdSingleLossRemote
                    Counter64,
                hwY1731TestIdSingleLossRemoteRatio
                    Unsigned32
             }

        hwY1731TestIdSingleLossSequence OBJECT-TYPE
            SYNTAX Unsigned32
            MAX-ACCESS  read-only
            STATUS      current
            DESCRIPTION
              "This object indicates the sequence number of the single-ended ETH-LM result."
            ::= { hwY1731TestIdSingleLossStatEntry 1 }  
            
          hwY1731TestIdSingleLossErrInfo OBJECT-TYPE
            SYNTAX Unsigned32
            MAX-ACCESS  read-only
            STATUS      current
            DESCRIPTION
              "This object indicates the sequence number of the single-ended ETH-LM result."
            ::= { hwY1731TestIdSingleLossStatEntry 2 }      

        hwY1731TestIdSingleLossLocal OBJECT-TYPE
            SYNTAX Counter64
            MAX-ACCESS  read-only
            STATUS      current
            DESCRIPTION
              "This object identifies the packet loss statistics that are collected on a local end.
              "
            ::= { hwY1731TestIdSingleLossStatEntry 3 }

          hwY1731TestIdSingleLossLocalRatio OBJECT-TYPE
            SYNTAX Unsigned32
            MAX-ACCESS  read-only
            STATUS      current
            DESCRIPTION
                "This object identifies the packet loss ratio that is collected on a local end."
            ::= { hwY1731TestIdSingleLossStatEntry 4 }
	    
         hwY1731TestIdSingleLossRemote OBJECT-TYPE
            SYNTAX Counter64
            MAX-ACCESS read-only
            STATUS current
            DESCRIPTION
                "This object identifies the packet loss statistics that are collected on a remote end."
            ::= { hwY1731TestIdSingleLossStatEntry 5 }

        hwY1731TestIdSingleLossRemoteRatio OBJECT-TYPE
            SYNTAX Unsigned32
            MAX-ACCESS read-only
            STATUS current
            DESCRIPTION
                "This object identifies the packet loss ratio that is collected on a remote end."
            ::= { hwY1731TestIdSingleLossStatEntry 6 }
     
         hwY1731TestIdOneDelayStatTable OBJECT-TYPE
            SYNTAX SEQUENCE OF HwY1731TestIdOneDelayStatEntry
            MAX-ACCESS not-accessible
            STATUS current
            DESCRIPTION
                "This table stores the result of one-way ETH-DM.
                "
            ::= { hwY1731StatisticObject 9 }
            
        hwY1731TestIdOneDelayStatEntry OBJECT-TYPE
            SYNTAX HwY1731TestIdOneDelayStatEntry
            MAX-ACCESS not-accessible
            STATUS current
            DESCRIPTION
                "An entry in the table, containing information about the result of one-way ETH-DM."
            INDEX { hwY1731TestIdentifier, hwY1731TestIdOneDelaySequence }
            ::= { hwY1731TestIdOneDelayStatTable 1 }

        HwY1731TestIdOneDelayStatEntry ::=
            SEQUENCE {
                hwY1731TestIdOneDelaySequence
                    Unsigned32,
                hwY1731TestIdOneDelayErrInfo   
                    Unsigned32,              
                hwY1731TestIdOneDelay
                    Integer32,
                hwY1731TestIdOneDelayVariation
                    Unsigned32
             }

        hwY1731TestIdOneDelaySequence OBJECT-TYPE
            SYNTAX Unsigned32
            MAX-ACCESS  read-only
            STATUS      current
            DESCRIPTION
              "This object indicates the sequence number of the one-way ETH-DM result."
            ::= { hwY1731TestIdOneDelayStatEntry 1 }
            	
          
       hwY1731TestIdOneDelayErrInfo OBJECT-TYPE
            SYNTAX Unsigned32
            MAX-ACCESS  read-only
            STATUS      current
            DESCRIPTION
              "This object indicates the statistics about the one-way delay."
            ::= { hwY1731TestIdOneDelayStatEntry 2 }  
	    
         hwY1731TestIdOneDelay OBJECT-TYPE
            SYNTAX Integer32
            MAX-ACCESS  read-only
            STATUS      current
            DESCRIPTION
              "This object indicates the statistics about the one-way delay."
            ::= { hwY1731TestIdOneDelayStatEntry 3 } 
	    
	  hwY1731TestIdOneDelayVariation OBJECT-TYPE
            SYNTAX Unsigned32
            MAX-ACCESS  read-only
            STATUS      current
            DESCRIPTION
              "This object indicates the variation about the one-way delay.
               After the device is enabled to receive packets, statistics collected for the first time are invalid, and the value is set to 0.
              "
            ::= { hwY1731TestIdOneDelayStatEntry 4 }   
	                       
        hwY1731TestIdTwoDelayStatTable OBJECT-TYPE
            SYNTAX SEQUENCE OF HwY1731TestIdTwoDelayStatEntry
            MAX-ACCESS not-accessible
            STATUS current
            DESCRIPTION
                "This table stores the result of two-way ETH-DM.
                "
            ::= { hwY1731StatisticObject 10 }
            
        hwY1731TestIdTwoDelayStatEntry OBJECT-TYPE
            SYNTAX HwY1731TestIdTwoDelayStatEntry
            MAX-ACCESS not-accessible
            STATUS current
            DESCRIPTION
                "An entry in the table, containing information about the result of two-way ETH-DM."
            INDEX { hwY1731TestIdentifier, hwY1731TestIdTwoDelaySequence }
            ::= { hwY1731TestIdTwoDelayStatTable 1 }

        HwY1731TestIdTwoDelayStatEntry ::=
            SEQUENCE {
                hwY1731TestIdTwoDelaySequence
                    Unsigned32, 
                hwY1731TestIdTwoDelayErrInfo  
                    Unsigned32,               
                hwY1731TestIdTwoDelay
                    Unsigned32,
                hwY1731TestIdTwoDelayVariation
                    Unsigned32
             }

        hwY1731TestIdTwoDelaySequence OBJECT-TYPE
            SYNTAX Unsigned32
            MAX-ACCESS  read-only
            STATUS      current
            DESCRIPTION
              "This object indicates the sequence number of the two-way ETH-DM result."
            ::= { hwY1731TestIdTwoDelayStatEntry 1 }
	    
	    hwY1731TestIdTwoDelayErrInfo OBJECT-TYPE
            SYNTAX Unsigned32
            MAX-ACCESS  read-only
            STATUS      current
            DESCRIPTION
              "This object indicates the sequence number of the two-way ETH-DM result."
            ::= { hwY1731TestIdTwoDelayStatEntry 2 }
            	
        hwY1731TestIdTwoDelay OBJECT-TYPE
            SYNTAX Unsigned32
            MAX-ACCESS  read-only
            STATUS      current
            DESCRIPTION
              "This object indicates the statistics about the two-way delay."
            ::= { hwY1731TestIdTwoDelayStatEntry 3 }    
	       
         hwY1731TestIdTwoDelayVariation OBJECT-TYPE
            SYNTAX Unsigned32
            MAX-ACCESS  read-only
            STATUS      current
            DESCRIPTION
              "This object indicates the variation about the two-way delay.
               After the device is enabled to receive packets, statistics collected for the first time are invalid, and the value is set to 0.
              "
            ::= { hwY1731TestIdTwoDelayStatEntry 4 }   
         
        
           hwY1731TestIdStatisticResetTable OBJECT-TYPE
           SYNTAX SEQUENCE OF HwY1731TestIdStatisticResetEntry
            MAX-ACCESS not-accessible
            STATUS current
            DESCRIPTION
                "This table stores the result of two-way ETH-DM.
                "
            ::= { hwY1731StatisticObject 11 }   
                 
            hwY1731TestIdStatisticResetEntry OBJECT-TYPE
            SYNTAX HwY1731TestIdStatisticResetEntry
            MAX-ACCESS not-accessible
            STATUS current
            DESCRIPTION
                "An entry in the table, containing information about the result of two-way ETH-DM."
            INDEX { hwY1731TestIdentifier  }
            ::= { hwY1731TestIdStatisticResetTable 1 }

            HwY1731TestIdStatisticResetEntry ::=
            SEQUENCE {
                hwY1731TestIdResetStatisticType
                INTEGER            
                 }

           hwY1731TestIdResetStatisticType OBJECT-TYPE
            SYNTAX INTEGER
            {
              invalid(1),
              singleloss(2),
              dualloss(3),
              onewaydelay(4),
              twowaydelay(5)
            }
            MAX-ACCESS read-write
            STATUS current
            DESCRIPTION
                "This object indicates the type of reset.
                 The value can be:
                    invalid
                    singleloss
                    dualloss
                    onewaydelay
                    twowaydelay
                 The default value is invalid."
            ::= { hwY1731TestIdStatisticResetEntry 1 }
      
        hwY1731AisMaxPktNum OBJECT-TYPE
            SYNTAX Unsigned32    
            MAX-ACCESS accessible-for-notify
            STATUS current
            DESCRIPTION
                "The MAXIMUM of AIS packets transmitted in one second."
            ::= { hwEthOamY1731 3 }    
            
        hwY1731PMModeEnable OBJECT-TYPE
            SYNTAX EnabledStatus 
            MAX-ACCESS read-write
            STATUS current
            DESCRIPTION
                "This object indicates whether the y1731 summary statistic data is managed by Performace(PM) module,
                If it is enabled(1), the y1731 summary statistic data is managed, saved ane sent to NMS by Performace(PM) module.               
                The default value is disabled(2).
                "
            ::= { hwEthOamY1731 4 } 
         
         hwY1731GlobalObject OBJECT IDENTIFIER ::= { hwEthOamY1731 5 } 
		 
         hwY1731MaxTestId  OBJECT-TYPE
             SYNTAX Unsigned32 
             MAX-ACCESS read-only
             STATUS current
             DESCRIPTION
                 "This object indicates the maximum value of TestId in current configuration.
		  The value can be 0 or rangs from 1 to 4294967295.
		  The value 0 is an invalid value.
                 "
             ::= { hwY1731GlobalObject 1 } 
			
	hwY1731LckMaxPktNum OBJECT-TYPE
	    SYNTAX Unsigned32
	    MAX-ACCESS accessible-for-notify
	    STATUS current
	    DESCRIPTION
	        "The max LCK packets transmitted or received in 1 second."
	    ::= { hwY1731GlobalObject 2 }

	hwY1731LckCurrentPktNum OBJECT-TYPE
	    SYNTAX Unsigned32
	    MAX-ACCESS accessible-for-notify
	    STATUS current
	    DESCRIPTION
	        "The current LCK packets transmitting or receiving."
	    ::= { hwY1731GlobalObject 3 }

	hwY1731LckUpperThreshold OBJECT-TYPE
	    SYNTAX Unsigned32
	    MAX-ACCESS accessible-for-notify
	    STATUS current
	    DESCRIPTION
	        "The object is used to set the upper threshold value of LCK packets.
		The value range is from 1 to 100. 
		The default means 80.
		"
	    ::= { hwY1731GlobalObject 4 }
		

	hwY1731LckLowerThreshold OBJECT-TYPE
	    SYNTAX Unsigned32
	    MAX-ACCESS accessible-for-notify
	    STATUS current
	    DESCRIPTION
	       "The object is used to set the lower threshold value of LCK packets.
	       The value range is from 1 to 100. 
	       The default means 70.
	       "
	    ::= { hwY1731GlobalObject 5 }
    END
